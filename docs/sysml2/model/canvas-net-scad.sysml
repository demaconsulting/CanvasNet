package CanvasNet {
    part def CanvasNetScadSystem {
        doc /* CanvasNetScad is a clean-room front end for the OpenSCAD language, delivered incrementally as the separate DemaConsulting.CanvasNet.Scad NuGet package (packable as of Phase 6). Phase 4 delivered parsing: the public ScadDocument unit parses OpenSCAD-language source from a string, a stream, or a file path and reports the first syntax error as a ScadSyntaxException with file, line, and column (fail-fast, no recovery), or, on success, the file-scope include/use directives (recorded, never resolved while parsing), module names, and function names. Phase 5 added evaluation: ScadDocument.Evaluate runs a document and returns the echo lines, warnings, unsupported-feature reports, and instance count, with immutable validated ScadEvaluationOptions (variable overrides, time, limits, handlers), resource limits (ScadLimits), cancellation, and typed errors (ScadEvaluationException, ScadUnsupportedFeatureException); its public surface is ScadDocument plus the ScadOpenOptions, ScadSourceLocation, ScadSyntaxException, ScadDirective, ScadDirectiveKind, ScadEvaluationOptions, ScadEvaluationResult, ScadLimits, ScadDiagnostic, ScadUnsupportedFeature, ScadUnsupportedFeatureException, ScadEvaluationException, and ScadRenderOptions types. The internal ScadLanguage subsystem contains the ScadLexer unit (tokens with one-based locations, strict numbers, strings with escapes, identifiers, keywords, operators, comments, and include/use directive tokens) and the ScadParser unit (recursive-descent statements and precedence-climbing expressions into an immutable, name-agnostic syntax tree, with a 256-level nesting limit and a 4,194,304-character source limit). The internal ScadEvaluation subsystem contains the ScadValue unit (the value model), the ScadEvaluator unit (scoping, special variables, functions, modules, control flow, comprehensions, and the geometry-agnostic instantiation tree, with a deterministic recursion limit and a bounded large-stack restart), the ScadBuiltinFunctions unit (mathematics, trigonometry in degrees, list and string functions, and a platform-independent random generator), and the ScadFileResolver unit (include/use resolution under the file-access policy of ScadOpenOptions.FileAccess, every regular local file by default). Phase 6 adds geometry and rendering: ScadDocument.BuildScene builds a Render3D Scene of the evaluated model and ScadDocument.Render draws it onto a Surface (fitted isometric view by default, or a caller-supplied camera), with the immutable validated ScadRenderOptions (composed evaluation options, camera, fitted-view angles and projection, scene options, flat-shape thickness) and the ScadLimits triangle limit; every problem of the build and of the renderer's operand checks is reported through the evaluation's handlers (warnings for invalid arguments, unsupported-feature reports with stable scad- identifiers for everything recognized but not built), in order, once, on the calling thread, and strict mode stops at the first one. The internal ScadGeometry subsystem contains the ScadGeometryBuilder unit (the iterative, recursion-free walk, implicit unions, modifiers, booleans, hull and minkowski, dimension rules, triangle budget, reporting, scene location map, and renderer options hand-off), the ScadPrimitives unit (cube, sphere, cylinder, polyhedron, square, circle, polygon, and the fragment rule), the ScadTransforms unit (translate, rotate, scale, mirror, multmatrix, resize, and color), the ScadExtrusions unit (linear_extrude and rotate_extrude distributed over a symbolic 2D tree), and the ScadTextGeometry unit (the text module: font resolution, glyph layout, and flat 2D glyph regions). The package is packable. Phase 7 adds the hull module (3D and 2D) and the minkowski module of convex 3D children, built on the Render3D ConvexHull and MinkowskiSum units, with the scad-hull-* and scad-minkowski-* reports. Phase 8 renders transparency: the alpha of a color, the background modifier (a translucent ghost that is not part of the model), and the highlight modifier (a translucent copy that shares its meshes), with the additive ScadRenderOptions HighlightColor and GhostColor, on the Render3D transparency and overlay support. The text module builds the glyph outlines of a TrueType font from the core Fonts subsystem (the bundled Liberation Sans by default) into flat 2D shapes, with the additive ScadRenderOptions FontResolution. The projection module builds the shadow of 3D children on the XY plane, or with cut = true their cross-section at z = 0, into 2D shapes (part of the ScadGeometryBuilder unit), and the viewport special variables $vpt, $vpr, $vpd, and $vpf are defined for every model (the ScadEvaluator defines and reads them back, and the ScadDocument unit chooses the camera from them, from the render options, and from the model, drawing a model that is entirely 2D as a flat top-down sheet and reporting the choice through the additive ScadRenderOptions ResolvedViewHandler, ScadResolvedView, and ScadViewSource). The 2D Minkowski sum, offset, surface, import, roof, textmetrics and fontmetrics, and the two modifiers on a 2D shape that is not extruded remain explicitly deferred or reported as unsupported - see docs/design/canvas-net-scad.md's Design Constraints (Supported And Deferred Features, Deliberate Strictness And Deviations) and Implementation Phase Plan. */

        comment testRef /* Test: test/DemaConsulting.CanvasNet.Scad.Tests/ScadSystemIntegrationTests.cs */
        comment designRef /* Design: docs/design/canvas-net-scad.md */
        comment verificationRef /* Verification: docs/verification/canvas-net-scad.md */
        comment reqRef /* Requirements: docs/reqstream/canvas-net-scad.yaml */
        comment /* Clean-Room Provenance: OpenSCAD is GPL-licensed and its manual is CC BY-SA. CanvasNetScad is an original implementation written from general language-design knowledge; no OpenSCAD source, grammar, manual text, example, test corpus, or library was consulted or copied - see the Clean-Room Provenance constraint in docs/design/canvas-net-scad.md. */
        comment /* CanvasNetScad references the sibling CanvasNet system (its Canvas subsystem, for the Surface that Render returns and the Rgba32 colors; its Fonts subsystem, for the TrueTypeFont files, glyph lookup, outlines, advances, and kerning, the SystemFontCatalog installed-font lookup, and the bundled Liberation fonts of the text module; and its Geometry subsystem, for the Path glyph outlines that a font returns; and its Files subsystem, for the FileReferenceResolver that performs every file access of include and use inside the ScadEvaluation subsystem, under the FileAccessPolicy of ScadOpenOptions.FileAccess) and the sibling CanvasNetRender3D system (the Scene, MeshNode, GroupNode, CsgNode, Mesh, tessellation and extrusion types the ScadGeometry subsystem builds from, and the SceneRenderer, Camera, and SceneRenderOptions that draw it) through ProjectReferences in its csproj - modeled below as non-owning dependency relationships, since both systems live in this same git repository (each distributed as its own NuGet package, and both listed as dependencies of the Scad package) rather than being third-party (OTS) or Shared Package dependencies. Only the ScadGeometry subsystem and the Render and BuildScene methods of ScadDocument use them (Fonts and Geometry only by the ScadTextGeometry unit, through public API only, with no InternalsVisibleTo grant); the ScadLanguage subsystem uses neither, and the ScadEvaluation subsystem uses only the core Files subsystem. All lexing, parsing, and evaluation is its own code on the BCL. CanvasNetScad must never reference CanvasNetSvg, CanvasNetPdf, CanvasNetPptx, CanvasNetVsdx, or CanvasNetCharts - see the CanvasNetScad System Design document's Dependencies section. */

        part scadDocument : ScadDocument;
        part scadLanguage : ScadLanguage;
        part scadEvaluation : ScadEvaluation;
        part scadGeometry : ScadGeometry;

        dependency usesCanvas from CanvasNetScadSystem to Canvas;
        dependency usesFiles from CanvasNetScadSystem to Files;
        dependency usesFonts from CanvasNetScadSystem to Fonts;
        dependency usesGeometry from CanvasNetScadSystem to Geometry;
        dependency usesRender3D from CanvasNetScadSystem to CanvasNetRender3DSystem;
        dependency usesImageSources from CanvasNetScadSystem to ImageSources;
    }
}
