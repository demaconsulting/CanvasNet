package CanvasNet {
    part def GenericFontFamilies {
        doc /* Classifies a font family name as sans-serif, serif or monospace when it is a CSS generic family keyword or, on request, a well-known alias (Arial, Times New Roman, Courier New, the Liberation family names, and similar), and splits a CSS font-family list at the commas outside quotes. The single table of generic-family policy behind FontResolver. Stateless and thread-safe. */
        comment sourceRef /* Source: src/DemaConsulting.CanvasNet/Fonts/GenericFontFamilies.cs */
        comment testRef /* Test: test/DemaConsulting.CanvasNet.Tests/Fonts/GenericFontFamiliesTests.cs */
        comment designRef /* Design: docs/design/canvas-net/fonts/generic-font-families.md */
        comment verificationRef /* Verification: docs/verification/canvas-net/fonts/generic-font-families.md */
        comment reqRef /* Requirements: docs/reqstream/canvas-net/fonts/generic-font-families.yaml */
    }
}
