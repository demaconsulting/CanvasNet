package CanvasNet {
    part def PathFiller {
        doc /* Public static Fill entry point rasterizing a closed Path onto a Surface with a solid color, using the AGG/FreeType-style analytic signed-area/coverage-accumulation scanline algorithm. Also covers the supporting FillRule enum and the internal EdgeFlattener/ScanlineRasterizer/ClipMask helpers inline; none has independent behavior of its own. ClipMask represents a PDF content stream's active clipping path as an analytic device-space rectangle (axis-aligned rectangle clips, no dense buffer; a full-surface rectangle means no clip) and/or a dense per-pixel antialiased coverage mask for general paths, and backs internal clip-aware Fill overloads consumed solely by DemaConsulting.CanvasNet.Pdf. Fill applies the rectangle geometrically (fill polygons are Sutherland-Hodgman clipped to it, so a fill edge coincident with a clip edge keeps its exact single coverage) and multiplies only the dense coverage of a general (non-rectangle-union) clip. A clip made only of axis-aligned rectangles (for example a W* band) is also decomposed into disjoint rectangles and applied geometrically, so its edges never attenuate coincident fill edges; unions of up to 256 rectangles (1024 pieces) are decomposed by a slab sweep, and ClipMask also exposes the clip intersected geometrically with a device rectangle so axis-aligned images get exact coverage of image-and-clip. ScanlineRasterizer resolves EvenOdd cells holding two or more vertical edges exactly by sorted in-cell parity toggling; dense curved clips and rotated images keep the per-pixel coverage product (documented limit). */

        comment sourceRef /* Source: src/DemaConsulting.CanvasNet/Drawing/PathFiller.cs, src/DemaConsulting.CanvasNet/Drawing/FillRule.cs, src/DemaConsulting.CanvasNet/Drawing/EdgeFlattener.cs, src/DemaConsulting.CanvasNet/Drawing/ScanlineRasterizer.cs, src/DemaConsulting.CanvasNet/Drawing/ClipMask.cs */
        comment testRef /* Test: test/DemaConsulting.CanvasNet.Tests/Drawing/PathFillerTests.cs, test/DemaConsulting.CanvasNet.Tests/Drawing/EdgeFlattenerTests.cs, test/DemaConsulting.CanvasNet.Tests/Drawing/ScanlineRasterizerTests.cs, test/DemaConsulting.CanvasNet.Tests/Drawing/ClipMaskTests.cs */
        comment designRef /* Design: docs/design/canvas-net/drawing/path-filler.md */
        comment verificationRef /* Verification: docs/verification/canvas-net/drawing/path-filler.md */
        comment reqRef /* Requirements: docs/reqstream/canvas-net/drawing/path-filler.yaml */
    }
}
