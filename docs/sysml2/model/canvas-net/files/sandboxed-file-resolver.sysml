package CanvasNet {
    part def SandboxedFileResolver {
        doc /* Obsolete (an Obsolete warning that names the migration to FileReferenceResolver with FileAccessPolicy.Combine(FileAccessPolicy.UnderRoots(...), FileAccessPolicy.NoSymlinks)); kept with unchanged, race-free behavior for one release, and no part of the library uses it any longer. The public SandboxedFileResolver (a sealed partial class) with its SandboxOptions (base directory, search paths, resolver callback, byte limit), SandboxedFile (key, directory, root, bytes), SandboxException, and SandboxFailureKind types: it finds and reads the file a relative path names, once per instance. In file-system mode it searches the directory of the file the path is relative to (or the base directory) and then each search path in order; with the caller's callback it never touches the file system and hands the callback only normalized logical paths. It rejects empty, absolute, rooted, drive, UNC, colon, and control-character (C0, DEL, C1) paths and a path that leaves its root, refuses any symbolic link or junction below a root (whatever its target, a dangling link included, checked top-down before the file is opened, failing closed when the probe cannot answer, and verified again on the real path of the open handle before a byte is read, so a link swapped in after the check is refused and an unknown real path fails closed) while trusting the root itself, and never consults environment variables or the current directory. Files are opened read-only with FileShare.ReadWrite and FileShare.Delete (without blocking on Linux and macOS) and read under MaxFileBytes (an endless stream stops one chunk past the limit); a missing file is null, while an unreadable one (an existing file whose open fails, which is never reported as missing, a directory in place of a file, a handle that is not a regular file, or a callback or callback stream that throws or fails to dispose), an oversize one, or a refused path is a SandboxException with a kind, a path, and a detail and no host directory in its message. Cancellation passes through unchanged. Not thread-safe per instance. */

        comment sourceRef /* Source: src/DemaConsulting.CanvasNet/Files/SandboxedFileResolver.cs, src/DemaConsulting.CanvasNet/Files/SandboxedFileResolver.Paths.cs, src/DemaConsulting.CanvasNet/Files/SandboxOptions.cs, src/DemaConsulting.CanvasNet/Files/SandboxedFile.cs, src/DemaConsulting.CanvasNet/Files/SandboxException.cs, src/DemaConsulting.CanvasNet/Files/SandboxFailureKind.cs, src/DemaConsulting.CanvasNet/Files/NamespaceDoc.cs */
        comment testRef /* Test: test/DemaConsulting.CanvasNet.Tests/Files/SandboxedFileResolverTests.cs, test/DemaConsulting.CanvasNet.Tests/Files/SandboxedFileResolverLinkTests.cs, test/DemaConsulting.CanvasNet.Tests/Files/SandboxedFileResolverRaceTests.cs, test/DemaConsulting.CanvasNet.Tests/Files/SandboxExceptionTests.cs, test/DemaConsulting.CanvasNet.Tests/Files/SandboxTestSupport.cs */
        comment designRef /* Design: docs/design/canvas-net/files/sandboxed-file-resolver.md */
        comment verificationRef /* Verification: docs/verification/canvas-net/files/sandboxed-file-resolver.md */
        comment reqRef /* Requirements: docs/reqstream/canvas-net/files/sandboxed-file-resolver.yaml */
    }
}
