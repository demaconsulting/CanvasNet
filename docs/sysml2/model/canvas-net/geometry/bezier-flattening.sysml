package CanvasNet {
    part def BezierFlattening {
        doc /* Adaptive, tolerance-driven flattening of quadratic and cubic Bezier curves into polylines, writing into a caller-supplied output collection. */

        comment sourceRef /* Source: src/DemaConsulting.CanvasNet/Geometry/BezierFlattening.cs */
        comment testRef /* Test: test/DemaConsulting.CanvasNet.Tests/Geometry/BezierFlatteningTests.cs */
        comment designRef /* Design: docs/design/canvas-net/geometry/bezier-flattening.md */
        comment verificationRef /* Verification: docs/verification/canvas-net/geometry/bezier-flattening.md */
        comment reqRef /* Requirements: docs/reqstream/canvas-net/geometry/bezier-flattening.yaml */
    }
}
