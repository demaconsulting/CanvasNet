package CanvasNet {
    part def Rect {
        doc /* Axis-aligned bounding rectangle (position plus size), with union, intersection, matrix transformation, containment testing, and a union-identity Empty sentinel. */

        comment sourceRef /* Source: src/DemaConsulting.CanvasNet/Geometry/Rect.cs */
        comment testRef /* Test: test/DemaConsulting.CanvasNet.Tests/Geometry/RectTests.cs */
        comment designRef /* Design: docs/design/canvas-net/geometry/rect.md */
        comment verificationRef /* Verification: docs/verification/canvas-net/geometry/rect.md */
        comment reqRef /* Requirements: docs/reqstream/canvas-net/geometry/rect.yaml */
    }
}
