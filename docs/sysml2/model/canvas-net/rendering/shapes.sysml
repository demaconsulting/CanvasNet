package CanvasNet {
    part def Shapes {
        doc /* Static convenience shape helpers exposing FillRect/StrokeRect/FillRoundRect/StrokeRoundRect/FillCircle/StrokeCircle extension methods on Canvas. Each helper builds its path via the corresponding Geometry.Path factory and honors the Canvas current transform. */

        comment sourceRef /* Source: src/DemaConsulting.CanvasNet/Rendering/Shapes.cs */
        comment testRef /* Test: test/DemaConsulting.CanvasNet.Tests/Rendering/ShapesTests.cs */
        comment designRef /* Design: docs/design/canvas-net/rendering/shapes.md */
        comment verificationRef /* Verification: docs/verification/canvas-net/rendering/shapes.md */
        comment reqRef /* Requirements: docs/reqstream/canvas-net/rendering/shapes.yaml */
    }
}
