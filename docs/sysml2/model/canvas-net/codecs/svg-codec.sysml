package CanvasNet {
    part def SvgCodec {
        doc /* Decode/rasterize-only loader for a common real-world subset of SVG documents, rasterizing them into Surface pixel buffers. */

        comment sourceRef /* Source: src/DemaConsulting.CanvasNet/Codecs/SvgCodec.cs, src/DemaConsulting.CanvasNet/Codecs/Svg/SvgCodec.Core.cs, src/DemaConsulting.CanvasNet/Codecs/Svg/SvgCodec.Parsing.cs, src/DemaConsulting.CanvasNet/Codecs/Svg/SvgCodec.Elements.cs, src/DemaConsulting.CanvasNet/Codecs/Svg/SvgCodec.Shapes.cs, src/DemaConsulting.CanvasNet/Codecs/Svg/SvgCodec.PathData.cs, src/DemaConsulting.CanvasNet/Codecs/Svg/SvgCodec.PathRender.cs, src/DemaConsulting.CanvasNet/Codecs/Svg/SvgCodec.Filters.cs, src/DemaConsulting.CanvasNet/Codecs/Svg/SvgCodec.Filters.ColorMatrix.cs, src/DemaConsulting.CanvasNet/Codecs/Svg/SvgCodec.Filters.ComponentTransfer.cs, src/DemaConsulting.CanvasNet/Codecs/Svg/SvgCodec.Filters.Morphology.cs, src/DemaConsulting.CanvasNet/Codecs/Svg/SvgCodec.Filters.Convolution.cs, src/DemaConsulting.CanvasNet/Codecs/Svg/SvgCodec.Filters.DisplacementMap.cs, src/DemaConsulting.CanvasNet/Codecs/Svg/SvgCodec.Filters.Tile.cs, src/DemaConsulting.CanvasNet/Codecs/Svg/SvgCodec.Filters.DropShadow.cs, src/DemaConsulting.CanvasNet/Codecs/Svg/SvgCodec.Filters.FeImage.cs, src/DemaConsulting.CanvasNet/Codecs/Svg/SvgCodec.Paint.cs, src/DemaConsulting.CanvasNet/Codecs/Svg/SvgCodec.Gradients.cs, src/DemaConsulting.CanvasNet/Codecs/Svg/SvgCodec.Markers.cs, src/DemaConsulting.CanvasNet/Codecs/Svg/SvgCodec.Text.cs, src/DemaConsulting.CanvasNet/Codecs/Svg/SvgCodec.Attributes.cs, src/DemaConsulting.CanvasNet/Codecs/Svg/SvgFontFace.cs, src/DemaConsulting.CanvasNet/Codecs/Svg/SvgFontStyle.cs, src/DemaConsulting.CanvasNet/Codecs/Svg/SvgCodec.ClippingAndMasking.cs, src/DemaConsulting.CanvasNet/Codecs/Svg/SvgCodec.Patterns.cs, src/DemaConsulting.CanvasNet/Codecs/Svg/SvgCodec.PreserveAspectRatio.cs, src/DemaConsulting.CanvasNet/Codecs/Svg/SvgCodec.Image.cs, src/DemaConsulting.CanvasNet/Codecs/Svg/SvgCodec.Filters.Lighting.cs, src/DemaConsulting.CanvasNet/Codecs/Svg/SvgCodec.Filters.Turbulence.cs, src/DemaConsulting.CanvasNet/Codecs/Svg/SvgCodec.Filters.Blend.cs, src/DemaConsulting.CanvasNet/Codecs/Svg/SvgCodec.Css.Parser.cs, src/DemaConsulting.CanvasNet/Codecs/Svg/SvgCodec.Css.Selectors.cs, src/DemaConsulting.CanvasNet/Codecs/Svg/SvgCodec.Css.Cascade.cs, src/DemaConsulting.CanvasNet/Codecs/ImageInfo.cs */
        comment testRef /* Test: test/DemaConsulting.CanvasNet.Tests/Codecs/SvgCodecTests.cs, test/DemaConsulting.CanvasNet.Tests/Codecs/SvgFixtureTests.cs */
        comment designRef /* Design: docs/design/canvas-net/codecs/svg-codec.md */
        comment verificationRef /* Verification: docs/verification/canvas-net/codecs/svg-codec.md */
        comment reqRef /* Requirements: docs/reqstream/canvas-net/codecs/svg-codec.yaml */
    }
}
