package CanvasNet {
    part def JpegCodec {
        doc /* Hand-rolled loader/saver for a common real-world subset of JPEG files, converting to and from Surface pixel buffers, and a reader of the EXIF orientation (ReadExifOrientation) that examines only the marker segments in front of the image data and never throws for malformed data. */

        comment sourceRef /* Source: src/DemaConsulting.CanvasNet/Codecs/JpegCodec.cs, src/DemaConsulting.CanvasNet/Codecs/Jpeg/JpegCodec.Huffman.cs, src/DemaConsulting.CanvasNet/Codecs/Jpeg/JpegCodec.Dct.cs, src/DemaConsulting.CanvasNet/Codecs/Jpeg/JpegCodec.Decoder.cs, src/DemaConsulting.CanvasNet/Codecs/Jpeg/JpegCodec.Decoder.Scan.cs, src/DemaConsulting.CanvasNet/Codecs/Jpeg/JpegCodec.Encoder.cs, src/DemaConsulting.CanvasNet/Codecs/Jpeg/JpegCodec.Exif.cs, src/DemaConsulting.CanvasNet/Codecs/ImageInfo.cs */
        comment testRef /* Test: test/DemaConsulting.CanvasNet.Tests/Codecs/JpegCodecTests.cs, test/DemaConsulting.CanvasNet.Tests/Codecs/JpegFixtureTests.cs, test/DemaConsulting.CanvasNet.Tests/Codecs/JpegCodecExifTests.cs */
        comment designRef /* Design: docs/design/canvas-net/codecs/jpeg-codec.md */
        comment verificationRef /* Verification: docs/verification/canvas-net/codecs/jpeg-codec.md */
        comment reqRef /* Requirements: docs/reqstream/canvas-net/codecs/jpeg-codec.yaml */
    }
}
