package CanvasNet {
    part def TiffCodec {
        doc /* Hand-rolled loader/saver for 8-bit-per-sample RGB, RGBA, and Grayscale, strip-based TIFF 6.0 files, converting to and from Surface pixel buffers. */

        comment sourceRef /* Source: src/DemaConsulting.CanvasNet/Codecs/TiffCodec.cs, src/DemaConsulting.CanvasNet/Codecs/Tiff/TiffCodec.DataSource.cs, src/DemaConsulting.CanvasNet/Codecs/Tiff/TiffCodec.Decode.cs, src/DemaConsulting.CanvasNet/Codecs/Tiff/TiffCodec.Ifd.cs, src/DemaConsulting.CanvasNet/Codecs/Tiff/TiffCodec.Compression.cs, src/DemaConsulting.CanvasNet/Codecs/Tiff/TiffCodec.Utils.cs, src/DemaConsulting.CanvasNet/Codecs/ZlibHelper.cs, src/DemaConsulting.CanvasNet/Codecs/LzwDecoder.cs, src/DemaConsulting.CanvasNet/Codecs/ImageInfo.cs */
        comment testRef /* Test: test/DemaConsulting.CanvasNet.Tests/Codecs/TiffCodecTests.cs, test/DemaConsulting.CanvasNet.Tests/Codecs/TiffFixtureTests.cs, test/DemaConsulting.CanvasNet.Tests/Codecs/LzwDecoderTests.cs */
        comment designRef /* Design: docs/design/canvas-net/codecs/tiff-codec.md */
        comment verificationRef /* Verification: docs/verification/canvas-net/codecs/tiff-codec.md */
        comment reqRef /* Requirements: docs/reqstream/canvas-net/codecs/tiff-codec.yaml */
    }
}
