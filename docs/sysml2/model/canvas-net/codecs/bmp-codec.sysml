package CanvasNet {
    part def BmpCodec {
        doc /* Hand-rolled loader/saver for uncompressed 24-bit and 32-bit Windows BMP files, converting to and from Surface pixel buffers. */

        comment sourceRef /* Source: src/DemaConsulting.CanvasNet/Codecs/BmpCodec.cs, src/DemaConsulting.CanvasNet/Codecs/ImageInfo.cs */
        comment testRef /* Test: test/DemaConsulting.CanvasNet.Tests/Codecs/BmpCodecTests.cs */
        comment designRef /* Design: docs/design/canvas-net/codecs/bmp-codec.md */
        comment verificationRef /* Verification: docs/verification/canvas-net/codecs/bmp-codec.md */
        comment reqRef /* Requirements: docs/reqstream/canvas-net/codecs/bmp-codec.yaml */
    }
}
