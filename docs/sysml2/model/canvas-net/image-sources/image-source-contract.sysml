package CanvasNet {
    /* cspell:ignore embedder */
    part def ImageSourceContract {
        doc /* The public contract of the ImageSources subsystem: IImageSource (a format or live source: a name, the lower-case file name extensions it claims, the lower-case URI schemes it claims, and Render), ImageSourceRequest (the raw link; for a file-based request the bytes, relative name, and folder of the file, for a scheme-claimed request nothing but the link; the requested size, the live shared pixel budget (Budget, an ImageBudget; RemainingPixels reads it live; EnsureWithinBudget charges each surface a source is about to allocate and records it in ChargedPixels), the scoped IImageResolver, the strictness switch, a cancellation token, the FileAccess policy (AllowAll by default, null refused) a source must use, with Directory as the base, for every further file it reads itself; OpenContent and the SizeFor sizing rule), ImageBudget (the live pixel counter a render shares), ImageSourceResult (the picture, notes, printed text, and format; the lists are copied into read-only snapshots), ImageSourceDiagnostic and ImageDiagnosticSeverity (a note also carries the optional Detail, Location as an ImageDiagnosticLocation, and Page), ImageFragment (the parsed fragment of a link: name=value parameters split at the ampersand and the first equals sign, decoded afterwards, with the limits of 2048 characters and 32 parameters, and the accessors GetValue and GetPositiveInt32), IFragmentImageSource (the parameter names a source uses), IImageSourceOptions (caller-defined options of a direct render), ImageSourceRefusedException (how a source declines a picture, for example a page that does not exist), IImageResolver (what a renderer calls), EmbeddedImage (a loaded image with link, format, size, and depth), ImageSourceException (link, embedder, and the original failure), ImageSourceBudgetException (the refusal of a source for a picture over the pixel budget), and ImageSourceSet (an ordered, immutable list that validates claims, lets the later source win, and finds the source of a file name by its longest suffix or of a scheme). Anyone can implement it outside this repository. ImageFragment.GetPrefixed returns the parameters whose name starts with a prefix (def. for the variables of a model, param. for the parameters of a chart) with the prefix removed, IFragmentImageSource.FragmentParameterPrefixes (empty by default) declares the prefixes a source understands whatever follows them, and ImageParameterValues reads the value grammars of a model variable (the grammar of -D) and of a chart parameter (the grammar of --param: scalars, text, JSON arrays and objects) and every prefixed parameter of a fragment, refusing an unusable value with image-fragment-invalid. ImageFragment.ReviewParameters reviews the parameters of a fragment against the declaration of a source (a parameter it does not use is image-fragment-unknown-parameter, a declared parameter given twice with different values is image-fragment-duplicate-parameter), the one check that FolderImageResolver makes for the links of a document and the Viewer makes for the input paths of the command line; a model variable can be a vector (a JSON array of numbers, flags, null, text, and vectors), so the viewport variables $vpt and $vpr can be set from -D and from a def. parameter. */

        comment sourceRef /* Source: src/DemaConsulting.CanvasNet/ImageSources/IImageSource.cs, src/DemaConsulting.CanvasNet/ImageSources/ImageSourceRequest.cs, src/DemaConsulting.CanvasNet/ImageSources/ImageBudget.cs, src/DemaConsulting.CanvasNet/ImageSources/ImageSourceResult.cs, src/DemaConsulting.CanvasNet/ImageSources/ImageSourceDiagnostic.cs, src/DemaConsulting.CanvasNet/ImageSources/ImageDiagnosticSeverity.cs, src/DemaConsulting.CanvasNet/ImageSources/ImageDiagnosticLocation.cs, src/DemaConsulting.CanvasNet/ImageSources/ImageFragment.cs, src/DemaConsulting.CanvasNet/ImageSources/IFragmentImageSource.cs, src/DemaConsulting.CanvasNet/ImageSources/ImageParameterValues.cs, src/DemaConsulting.CanvasNet/ImageSources/IImageSourceOptions.cs, src/DemaConsulting.CanvasNet/ImageSources/ImageSourceRefusedException.cs, src/DemaConsulting.CanvasNet/ImageSources/IImageResolver.cs, src/DemaConsulting.CanvasNet/ImageSources/EmbeddedImage.cs, src/DemaConsulting.CanvasNet/ImageSources/ImageSourceException.cs, src/DemaConsulting.CanvasNet/ImageSources/ImageSourceBudgetException.cs, src/DemaConsulting.CanvasNet/ImageSources/ImageSourceSet.cs, src/DemaConsulting.CanvasNet/ImageSources/NamespaceDoc.cs */
        comment testRef /* Test: test/DemaConsulting.CanvasNet.Tests/ImageSources/ImageSourceSetTests.cs, test/DemaConsulting.CanvasNet.Tests/ImageSources/ImageSourceContractTests.cs, test/DemaConsulting.CanvasNet.Tests/ImageSources/ImageFragmentTests.cs, test/DemaConsulting.CanvasNet.Tests/ImageSources/ImageFragmentPrefixTests.cs, test/DemaConsulting.CanvasNet.Tests/ImageSources/ImageSourceTestSupport.cs */
        comment designRef /* Design: docs/design/canvas-net/image-sources/image-source-contract.md */
        comment verificationRef /* Verification: docs/verification/canvas-net/image-sources/image-source-contract.md */
        comment reqRef /* Requirements: docs/reqstream/canvas-net/image-sources/image-source-contract.yaml */
    }
}
