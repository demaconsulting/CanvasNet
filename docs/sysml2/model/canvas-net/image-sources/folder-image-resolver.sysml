package CanvasNet {
    part def FolderImageResolver {
        doc /* The resolver that loads the pictures a document links to, safely, through pluggable sources, with its FolderImageResolverOptions (MaxDepth 4, MaxImages 64, MaxDecodedPixels 64,000,000, ThrowOnUnsupportedFeature, CancellationToken, FileAccess: the file-access policy, AllowAll by default like Pandoc, null refused). A link without a URI scheme is read as a URI reference (the query and the fragment are cut off before percent-decoding; the fragment is parsed into the ImageFragment of the request, and a fragment over its limits is the unsupported note image-fragment-invalid) and is a path relative to the folder (or the folder of the embedding file; the folder is the base, not a boundary) resolved through the FileReferenceResolver of the Files subsystem under the policy: by default a dot-dot, absolute, drive, local file: URI (no host), or symbolic-link path is followed; UNC, //host, file: URIs with a host (localhost included), device, alternate-stream, control-character, and non-regular-file paths are unresolved warnings under every policy that never read a file; a file the policy denies (or cannot judge because its real path is unknown) is the warning image-access-denied (AccessDeniedCode) with nothing read or drawn, whose message names the link, the policy, its reason and a hint and whose Detail alone carries the host paths; and the source is chosen by the longest claimed extension before any file is read. A link whose URI scheme a source claims is handed to it as written with no file access; any other scheme (http and https included, for the built-in sources) is an unresolved warning. The later source of a sequence wins. Each source receives a request with a scoped resolver that shares the depth, cycle chain, count, and lists of the render, and with FileAccess set to the policy anchored at the origin of the chain (FileAccessPolicy.AnchoredAt; the raw policy for a scheme-claimed request), so a linked model or chart reads its own includes and data under the same policy judged from the host-chosen origin; cycles (compared on the real path of the file, so a file reached again through a link is a cycle), depth, and count are unresolved warnings; the pixels the sources allocate are limited by one live budget (an ImageBudget created from MaxDecodedPixels and shared by every request, nested ones included) that every source charges when it allocates (ImageSourceRequest.EnsureWithinBudget, recorded in ChargedPixels; ImageSourceBudgetException when it does not fit) and that the resolver settles around each source: it refuses a link whose requested size cannot fit before calling the source, charges the excess of the returned surface over what the source charged, and gives back what a failed source charged; the resolver reports the live free part as RemainingPixels, and the refusal is the warning svg-image-too-large (an ImageSourceBudgetException for a direct render); the depth and count limits are applied before an embedded file is read; notes are forwarded with the embedding link in front; before a source is called the resolver warns about each fragment parameter the source does not declare through IFragmentImageSource (image-fragment-unknown-parameter) and each parameter given twice with different values (image-fragment-duplicate-parameter, the last wins), and an ImageSourceRefusedException of a source (a page that does not exist, image-page-out-of-range, or an unusable value, image-fragment-invalid) is an unsupported note with nothing drawn; a direct render passes caller-defined IImageSourceOptions to the source and an embedded file never inherits them; a failure of a found file is an ImageSourceException (never for cancellation); nothing is cached. Render(path) and Render(Stream) draw a top-level file and fail loudly; the file of Render(path) (relative to the folder or absolute) is the caller's choice, read through FileReferenceResolver.ResolveTopLevel and never judged by the policy, while its links are judged from its own folder. One resolver serves one render and is not thread-safe. A parameter whose name starts with a prefix the source declares (IFragmentImageSource.FragmentParameterPrefixes, for example def. or param.) is understood and gets no unknown-parameter warning; the part after the prefix is compared as written when looking for a duplicate. Requested lists every link a document asked for at any level as a RequestedImage (the link, the files that contain it, and the name of the picture when it was drawn), so a caller can find the links an embedded file never showed. */

        comment sourceRef /* Source: src/DemaConsulting.CanvasNet/ImageSources/FolderImageResolver.cs, src/DemaConsulting.CanvasNet/ImageSources/FolderImageResolver.Href.cs, src/DemaConsulting.CanvasNet/ImageSources/FolderImageResolverOptions.cs, src/DemaConsulting.CanvasNet/ImageSources/RequestedImage.cs */
        comment testRef /* Test: test/DemaConsulting.CanvasNet.Tests/ImageSources/FolderImageResolverTests.cs, test/DemaConsulting.CanvasNet.Tests/ImageSources/FolderImageResolverHrefTests.cs, test/DemaConsulting.CanvasNet.Tests/ImageSources/FolderImageResolverBudgetTests.cs, test/DemaConsulting.CanvasNet.Tests/ImageSources/FolderImageResolverFileAccessTests.cs, test/DemaConsulting.CanvasNet.Tests/ImageSources/FolderImageResolverFragmentTests.cs, test/DemaConsulting.CanvasNet.Tests/ImageSources/ImageFragmentPrefixTests.cs, test/DemaConsulting.CanvasNet.Tests/ImageSources/PngHeaderFixtures.cs, test/DemaConsulting.CanvasNet.Tests/ImageSources/ImageSourceTestSupport.cs */
        comment designRef /* Design: docs/design/canvas-net/image-sources/folder-image-resolver.md */
        comment verificationRef /* Verification: docs/verification/canvas-net/image-sources/folder-image-resolver.md */
        comment reqRef /* Requirements: docs/reqstream/canvas-net/image-sources/folder-image-resolver.yaml */
    }
}
