package CanvasNet {
    part def ImagePipeline {
        doc /* The ordered image pipeline: parses the transformation options of a command line (crop as x,y,w,h or WxH+X+Y in pixels or percent, resize to an exact size, fit inside a box that only shrinks unless upscaling is allowed, rotate clockwise by any angle, flip, pad with a border color, the tone adjustments grayscale, invert, threshold (a level or auto), levels, brightness, contrast, and auto-levels, deskew, trim, and a labeled coordinate grid, with the resampling filter chosen by name and the settings of the rotation fill, the auto-levels clip, and the trim tolerance) into operations, and applies them left to right to a Surface. A right angle is an exact pixel move; any other angle (and the correction of a skew) is rotated by the core Surface (the SurfaceGeometry unit) onto an expanded canvas with a fill color (the fill of the operation, else the background the user gave, else opaque white for an image with no transparent pixel, else transparent). The tone adjustments, deskew, trim, and grid are carried out by the core Surface (adjustments, trim, rotation, skew estimation) and the GridOverlay unit; an operation that changes pixels in place works on a surface the pipeline owns (an intermediate, or a copy of the input), so the input is never modified and at most two full-size surfaces exist at a time, with every intermediate disposed. A crop past an edge is cut off, a crop outside the image, a malformed or out-of-range value, and a setting without its operation are usage errors, and a size, border, or explicitly requested rotated canvas beyond 8192 pixels is refused before allocation; an automatic deskew that would exceed the limit is instead skipped, copied unchanged, and reported with a reason. The unit reports every operation applied with its parameters and the size of its result, including the level an automatic threshold chose, the points auto-levels found, and the skew angle and confidence of a deskew. The render command, the inspect command, and the verb commands crop, resize, rotate, flip, and pad share it. The unit includes the operation records in ImageOperations.cs. */

        comment sourceRef /* Source: src/DemaConsulting.CanvasNet.Tool/Imaging/ImagePipeline.cs, src/DemaConsulting.CanvasNet.Tool/Imaging/ImagePipeline.Anchors.cs, src/DemaConsulting.CanvasNet.Tool/Imaging/ImageOperations.cs */
        comment testRef /* Test: test/DemaConsulting.CanvasNet.Tool.Tests/Imaging/ImagePipelineTests.cs, test/DemaConsulting.CanvasNet.Tool.Tests/Imaging/ImagePipelineAnchorTests.cs */
        comment designRef /* Design: docs/design/canvas-net-tool/imaging/image-pipeline.md */
        comment verificationRef /* Verification: docs/verification/canvas-net-tool/imaging/image-pipeline.md */
        comment reqRef /* Requirements: docs/reqstream/canvas-net-tool/imaging/image-pipeline.yaml */
    }
}
