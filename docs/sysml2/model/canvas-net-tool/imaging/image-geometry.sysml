package CanvasNet {
    part def ImageGeometry {
        doc /* The geometry of a surface beyond right-angle moves. RotatedSize calculates the canvas of an image rotated by any finite angle as the ceiling of the bounding box of the rotated rectangle (a tolerance of 1e-9 so an exact fit gains no pixel) and CheckRotatedSize refuses a canvas larger than 8192 pixels on a side with the size-limit error and a hint to shrink first, before anything is allocated. RotateArbitrary rotates clockwise about the centers of the image and the expanded canvas, calculating every destination pixel from its own coordinates, with nearest sampling or bilinear sampling in premultiplied form in which a tap outside the image is the fill color so that the rotated edge fades into it, storing a fully transparent pixel as transparent black, with fast paths for all-inside and all-outside taps that give the pixels of the generic sampler. EstimateSkew finds the skew of the dominant near-horizontal structure within 15 degrees: it averages the luma of the image into a gray analysis plane of at most 1024 pixels on its longest side, marks the pixels that are at least 10 levels darker than the mean of the window of radius 8 around them, scores each candidate angle by the sum of the squared counts of the whole-pixel profile bins of the marks (in 2^20 fixed point, so library rounding cannot move a mark), searches every degree and then refines to 0.25 and 0.05 degrees with ties going to the smaller absolute angle, reports the angle in hundredths of a degree (positive when the lines descend to the right) with a confidence from the best score and the median of the first-stage scores, and reports an image with too few marks as not estimated. Rows are processed in parallel with disjoint output, so results do not depend on the number of cores. The unit works on surfaces only and is deterministic. */

        comment sourceRef /* Source: src/DemaConsulting.CanvasNet.Tool/Imaging/ImageGeometry.cs, src/DemaConsulting.CanvasNet.Tool/Imaging/ImageGeometry.Deskew.cs */
        comment testRef /* Test: test/DemaConsulting.CanvasNet.Tool.Tests/Imaging/ImageGeometryTests.cs, test/DemaConsulting.CanvasNet.Tool.Tests/Imaging/ImageGeometryDeskewTests.cs */
        comment designRef /* Design: docs/design/canvas-net-tool/imaging/image-geometry.md */
        comment verificationRef /* Verification: docs/verification/canvas-net-tool/imaging/image-geometry.md */
        comment reqRef /* Requirements: docs/reqstream/canvas-net-tool/imaging/image-geometry.yaml */
    }
}
