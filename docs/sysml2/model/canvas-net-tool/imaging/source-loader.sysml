package CanvasNet {
    part def SourceLoader {
        doc /* Turns a path into facts or into pixels for the files the tool reads. Detect recognizes the format from the signature bytes, then the entries of a ZIP package (presentation or drawing), then SVG text, then the extension (a file named .scad is a model); a file named .vl.json or .vl, or a .json file whose top-level $schema property names a Vega-Lite schema (read from the first 4 KiB), is a Vega-Lite chart (never taken for an SVG; a plain Vega specification is an unsupported format); Probe reads the header facts (format, size, channels, transparency, decodability, frame count, EXIF orientation, for a PDF, PPTX, or VSDX document every page with its size, rotation, and name, for an OpenSCAD model, by parsing it, the names of its modules and functions and its include and use directives, and for a Vega-Lite chart, by parsing and measuring it, the laid-out size and its marks, data references, parameters, title, and schema version) without decoding; Load and OpenPages decode a raster at its own size, render an SVG directly at the target size (an image element of an SVG file that names a relative file - a raster, an SVG file, an OpenSCAD model, a Vega-Lite chart, or the first page of a document - is loaded by the image resolver that CanvasNetViewer.CreateImageResolver creates for the folder of the SVG file and that this unit hands to the SVG library through SvgLoadOptions.ImageResolver; the sandbox, the limits, the dispatch by file name extension (the extensions of CanvasNetViewer.Extensions, documented in the svg help topic), and the nesting belong to the core ImageSources subsystem, and this unit only maps what the resolver reports to its own notes, text, and embed operations, turns an unresolved reference into an unsupported-feature error when strict, maps the failure of a file that is found but cannot be drawn to the error code of that failure naming both files, and keeps the tool free of any plug-in mechanism), render a chosen page of a document at a resolution (opening the document once for all its pages), or draw an OpenSCAD model from a named view (iso, front, back, left, right, top, or bottom, with the azimuth and elevation replaceable, orthographic or perspective; the view is passed to the SCAD library only when a view name, azimuth, or elevation is given, so that otherwise the library chooses it - iso for a model with 3D objects, top for a model that is entirely 2D, or the model's own $vpr view - and the view it used is reported in the operation) at 800 by 800 pixels by default with variables, time, default color, and a triangle limit applied and with its include and use files read from the folder of the model and below only, or draw a Vega-Lite chart at its laid-out size or the size asked for over its own background (UTC dates, bundled fonts only, no network, and the data files of the chart read by the library from the folder of the specification and below only, with no data-folder option), applying the size policy (scale, width, height, fitting a page inside a box, rounding, the 8192-pixel limit before decoding), the EXIF orientation of a JPEG (read by the core JpegCodec and applied by the core Surface), and the background color, collecting the notes about skipped or approximated features and the warnings and echo of a model (or refusing the features when strict), and reporting the operations applied. It maps an explicit list of library exceptions (missing, unreadable, unsupported feature, corrupt data, SCAD syntax and evaluation errors, Vega-Lite specification and render errors - a local data file that is missing, outside the folder of the specification, or not valid is a vega-lite-error and a data limit is budget-exceeded - exceeded limits) to expected errors and lets every other exception propagate. The unit includes BoxOptions (the options that load a source into a box: vector sources are rendered natively at the box), and the supporting model types SourceKind, OutputFormat, SourceInfo, SourceOptions, ScadViewOptions, ScadView, SourceDirective, ChartFacts, ChartDataReference, LoadedSource, AppliedOperation, ImageDiagnostic, and SourcePage. */

        comment sourceRef /* Source: src/DemaConsulting.CanvasNet.Tool/Imaging/SourceLoader.cs, src/DemaConsulting.CanvasNet.Tool/Imaging/SourceLoader.Detect.cs, src/DemaConsulting.CanvasNet.Tool/Imaging/SourceLoader.Raster.cs, src/DemaConsulting.CanvasNet.Tool/Imaging/SourceLoader.Svg.cs, src/DemaConsulting.CanvasNet.Tool/Imaging/SourceLoader.SvgImages.cs, src/DemaConsulting.CanvasNet.Tool/Imaging/SourceLoader.Documents.cs, src/DemaConsulting.CanvasNet.Tool/Imaging/SourceLoader.Pdf.cs, src/DemaConsulting.CanvasNet.Tool/Imaging/SourceLoader.Pptx.cs, src/DemaConsulting.CanvasNet.Tool/Imaging/SourceLoader.Vsdx.cs, src/DemaConsulting.CanvasNet.Tool/Imaging/SourceLoader.Scad.cs, src/DemaConsulting.CanvasNet.Tool/Imaging/SourceLoader.VegaLite.cs, src/DemaConsulting.CanvasNet.Tool/Imaging/SourceModels.cs */
        comment testRef /* Test: test/DemaConsulting.CanvasNet.Tool.Tests/Imaging/SourceLoaderTests.cs, test/DemaConsulting.CanvasNet.Tool.Tests/Imaging/SourceLoaderVectorTests.cs, test/DemaConsulting.CanvasNet.Tool.Tests/Imaging/SourceLoaderScadTests.cs, test/DemaConsulting.CanvasNet.Tool.Tests/Imaging/SourceLoaderVegaLiteTests.cs, test/DemaConsulting.CanvasNet.Tool.Tests/Imaging/SourceLoaderSvgImageTests.cs */
        comment designRef /* Design: docs/design/canvas-net-tool/imaging/source-loader.md */
        comment verificationRef /* Verification: docs/verification/canvas-net-tool/imaging/source-loader.md */
        comment reqRef /* Requirements: docs/reqstream/canvas-net-tool/imaging/source-loader.yaml */
    }
}
