package CanvasNet {
    part def HelpTopics {
        doc /* The catalog of help topics of the tool, shipped inside the tool as embedded resources so that it works offline and matches the installed version: twelve topics in a fixed order (scad, vega-lite, mermaid, svg, pdf, pptx, vsdx, raster, json, errors, limits, and files), each with a title, a summary, aliases (for example openscad, vl, mmd, powerpoint, visio, and png or jpg for raster), sections, and examples. A topic of an input format has the sections supported, unsupported, options, diagnostics (and how --strict treats them), and known differences, and at least two examples; the topics json, errors, and limits describe the result documents, the error codes and exit codes, and the size and resource limits. The numbers in the text are tokens resolved from the constants of the code when the topic loads. An example is source text (shipped as a file next to the topic and verified to render with --strict without a diagnostic), a snippet (text that refers to other files, such as the embed diagram of the svg topic that links a model, a chart, and an SVG file and the embed-pages diagram whose links choose pages with #page=N and #slide=N, and the pictures diagram of the mermaid topic whose nodes show a model and a chart; it is shown but verified by a dedicated test that renders it with its sibling files), or a command line. The svg topic has a section image-links that lists the file types an image href may link (compared in both directions with the extensions the SVG image resolver of the SourceLoader unit accepts), the size rule, the link rule, the page fragment (grammar, the parameter of each format, limits, the XML ampersand note), the svg-image-unresolved warning, and in its diagnostics section the codes image-fragment-unknown-parameter, image-fragment-duplicate-parameter, image-fragment-invalid, and image-page-out-of-range with the effect of --strict; the pdf, pptx, vsdx, and scad topics show the fragment of their format, the json topic describes the detail, location, and origin members of a diagnostic, the limits topic states the fragment limits, and the scad and vega-lite topics point to the svg topic. The unit finds a topic by name or alias ignoring case (names and aliases never collide with a command, help, or topics), and renders a topic, the list of its examples, and one example as plain text (no color codes, wrapped to 78 columns without splitting a word, deterministic) or as a JSON document (kinds topic, examples, and example); an unknown example name is a usage error listing the names. The content is verified against the code (the options of the render command, every error code, the cited diagnostic identifiers and what triggers them, and the limits) so that it cannot drift. It is used by the CommandRegistry unit, which owns the help command, and by the help examples self-test of the Validation unit. The vega-lite topic documents --param and the vl-param-unknown diagnostic, the mermaid topic documents --theme, the theme fragment, the diagram types and constructs that are not drawn, and the limits of the Mermaid library, the svg topic documents the def. and param. fragment parameters of an image link, and the scad topic shows the def. fragment. The svg topic also documents the fragment of an input path of the command line (the rule for the number sign, the overrides, the quoting, the codes), the scad topic a fixed camera for a montage with the viewport variables, the document and chart topics the command-line form, and the errors topic the code image-fragment-invalid. The files topic (aliases file-access and links) describes the file-access modes, the options --file-access and --allow-root, what holds in every mode, the diagnostics image-access-denied and file-access-denied, and the variables of the Pandoc filter; its items equal, in order, the rows of the File Access Reference table of the tool user guide, which a unit test checks. */

        comment sourceRef /* Source: src/DemaConsulting.CanvasNet.Tool/Commands/HelpTopics.cs, src/DemaConsulting.CanvasNet.Tool/Commands/HelpTopics.Render.cs, src/DemaConsulting.CanvasNet.Tool/Commands/Help/ (the embedded topic files and the examples in Help/Examples/) */
        comment testRef /* Test: test/DemaConsulting.CanvasNet.Tool.Tests/Commands/HelpTopicsTests.cs, test/DemaConsulting.CanvasNet.Tool.Tests/Commands/HelpTopicsTests.Triggers.cs, test/DemaConsulting.CanvasNet.Tool.Tests/Commands/InputFragmentTests.cs */
        comment designRef /* Design: docs/design/canvas-net-tool/commands/help-topics.md */
        comment verificationRef /* Verification: docs/verification/canvas-net-tool/commands/help-topics.md */
        comment reqRef /* Requirements: docs/reqstream/canvas-net-tool/commands/help-topics.yaml */
    }
}
