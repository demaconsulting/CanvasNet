package CanvasNet {
    part def RenderCommand {
        doc /* The render command and its alias convert, and the verb commands crop, resize, rotate, flip, and pad that are the same unit constructed with a verb: loads an image, drawing, document page, OpenSCAD model view, Vega-Lite chart, or Mermaid diagram, applies the image pipeline, and writes it as PNG, JPEG, BMP, or TIFF in one pass for one page or every page. It declares its options (page, all-pages, dpi, scale, width, height, size, background, no-auto-orient, strict, file-access, allow-root, the model options view, azimuth, elevation, projection, define (-D), time, default-color, and max-triangles, the chart option param, the diagram option theme, the pipeline options crop, resize, fit, allow-upscale, rotate, rotate-fill, flip, pad, pad-color, the photo tools grayscale, invert, threshold, levels, brightness, contrast, auto-levels, auto-levels-clip, deskew, trim, trim-tolerance, and grid, and filter, output, format, quality, no-clobber) in one table, shared by the verbs and the inspect command, that also drives the help, reads the source options in one reusable routine, reads and validates them (rejecting contradictory size options, malformed values, a view or projection that does not exist, a page together with all pages, a model option for an input that is not a model (a chart has no options of its own), a rotation fill without a rotation, and sizes beyond the maximum; a view, azimuth, or elevation option marks the view of a model as given, and without one the SCAD library chooses the view and the operation reports the one it used), reports every mistake about the input, the pages, and every output before decoding anything, plans the output file of each page ({page} placeholder or a directory), loads the source once through the SourceLoader, applies the ImagePipeline operations in the order written (a verb's operand is the first operation; the background the user gave is the fill of a rotation), writes each page through the ImageWriter (every page is staged first and all are published together only when every page succeeded, so a failing page leaves no new or partial output), and reports the result as one text line per output or, when the JSON option is given, as one JSON document with the tool, the input (with the page and page count of a document), the operations applied in order (the loader's, the pipeline's with their parameters and sizes, and the flatten of a JPEG), the outputs, the diagnostics with their pages, and the echoed text. Its option declarations (SpecsFor), the reader of the model options, and the writer of an operation parameter are shared with the CompareCommand and MontageCommand units. The repeatable --param name=value option sets the parameters of a Vega-Lite chart (ReadChartOptions, SourceOptions.VegaLite): the chart is laid out again with them, the render operation lists them in params, an unknown name is a vega-lite-error that lists the declared names, and the option is a usage error for an input that is not a chart (render, the verb commands and inspect). The --theme name option sets the theme of a Mermaid diagram (ReadDiagramOptions, SourceOptions.Mermaid; one of default, base, dark, forest, and neutral in any case): a theme fragment of the input wins over it and a theme the text sets wins over both, the render operation lists the theme, and a name that is not a theme or the option on an input that is not a diagram is a usage error (render, the verb commands and inspect). The input path may end in a URL fragment (part.scad#view=top&def.width=20, report.pdf#page=3, chart.vl.json#param.cutoff=5, flow.mmd#theme=dark) read with the grammar and the checks of the link of an SVG image (a number sign starts it only when no file has that exact name): it overrides --page, --view, -D, --param and --theme for that input and makes a page it names the only page, an unusable value is image-fragment-invalid and a missing page page-out-of-range, an unknown or repeated parameter or an undeclared chart parameter is a warning (also with --strict), the input is named with its fragment in the text result and the JSON input object has a fragment member. It reads the file-access options --file-access (any, roots, no-symlinks, or roots,no-symlinks) and the repeatable --allow-root (which implies roots and replaces the default folders, the working directory and the folder of each input outside it) in RenderCommand.FileAccess.cs, the routine every reading command shares; an unknown mode, --allow-root with any or no-symlinks, and a missing folder are usage errors before any input is opened, and the policy reaches the probe and the load through SourceOptions.FileAccess and is never written into the JSON result. */

        comment sourceRef /* Source: src/DemaConsulting.CanvasNet.Tool/Commands/RenderCommand.cs, src/DemaConsulting.CanvasNet.Tool/Commands/RenderCommand.Options.cs, src/DemaConsulting.CanvasNet.Tool/Commands/RenderCommand.FileAccess.cs, src/DemaConsulting.CanvasNet.Tool/Commands/RenderCommand.Verbs.cs, src/DemaConsulting.CanvasNet.Tool/Commands/ImagePipelineParser.cs */
        comment testRef /* Test: test/DemaConsulting.CanvasNet.Tool.Tests/Commands/RenderCommandTests.cs, test/DemaConsulting.CanvasNet.Tool.Tests/Commands/RenderCommandFileAccessTests.cs, test/DemaConsulting.CanvasNet.Tool.Tests/Commands/RenderCommandScadAnchorTests.cs, test/DemaConsulting.CanvasNet.Tool.Tests/Commands/RenderCommandDocumentTests.cs, test/DemaConsulting.CanvasNet.Tool.Tests/Commands/RenderCommandScadTests.cs, test/DemaConsulting.CanvasNet.Tool.Tests/Commands/RenderCommandVegaLiteTests.cs, test/DemaConsulting.CanvasNet.Tool.Tests/Commands/RenderCommandMermaidTests.cs, test/DemaConsulting.CanvasNet.Tool.Tests/Commands/RenderCommandPipelineTests.cs, test/DemaConsulting.CanvasNet.Tool.Tests/Imaging/ImagePipelineTests.cs, test/DemaConsulting.CanvasNet.Tool.Tests/Commands/InputFragmentTests.cs */
        comment designRef /* Design: docs/design/canvas-net-tool/commands/render-command.md */
        comment verificationRef /* Verification: docs/verification/canvas-net-tool/commands/render-command.md */
        comment reqRef /* Requirements: docs/reqstream/canvas-net-tool/commands/render-command.yaml */
    }
}
