package CanvasNet {
    part def InspectCommand {
        doc /* The inspect command with the subcommands colors and pixel, registered once because the command table is flat: the first positional argument is the subcommand (in any case; a missing or unknown one is a usage error with the closest name suggested, as is an option of the other subcommand). It loads one page of its input exactly as the render command does (the source options and the EXIF orientation, drawings and models rendered, a page of a document), applies the image pipeline given as options in the order written, and reports what the pixels contain without writing any file: colors reports the dominant colors (at most count, from 1 to 32, default 8) with their pixel counts and shares and the luma statistics (mean, range, percentiles 1, 50, and 99, the Otsu level, and a 16-bin histogram) of the image with translucent pixels flattened over the background, and pixel reports the pixel at a point x,y (as stored, with its hex color, channels, alpha, and luma over white) and, with a radius from 1 to 8, the clipped window around it with its mean and pixels, a point outside the image being a usage error. Its options are the source and pipeline options of the render command (the same declarations, without the options of the output) plus count and radius. The result is one or two text lines or one JSON document with the subcommand, the tool, the input, the operations, the image size, and the colors and luma or the point, pixel, and neighborhood. It uses the SourceLoader and ImagePipeline units and the analysis of the core Surface (the SurfaceAnalysis unit). The input path may end in a URL fragment, read as for the render command, that chooses the page, the model variables and view, and the chart parameters that are inspected. The file-access options of render apply to its input (the probe and the load), so a picture the mode denies is left out of the analysis and reported as image-access-denied. */

        comment sourceRef /* Source: src/DemaConsulting.CanvasNet.Tool/Commands/InspectCommand.cs, src/DemaConsulting.CanvasNet.Tool/Commands/InspectCommand.Options.cs */
        comment testRef /* Test: test/DemaConsulting.CanvasNet.Tool.Tests/Commands/InspectCommandTests.cs, test/DemaConsulting.CanvasNet.Tool.Tests/Commands/InspectCommandSourceTests.cs, test/DemaConsulting.CanvasNet.Tool.Tests/Commands/InputFragmentTests.cs */
        comment designRef /* Design: docs/design/canvas-net-tool/commands/inspect-command.md */
        comment verificationRef /* Verification: docs/verification/canvas-net-tool/commands/inspect-command.md */
        comment reqRef /* Requirements: docs/reqstream/canvas-net-tool/commands/inspect-command.yaml */
    }
}
