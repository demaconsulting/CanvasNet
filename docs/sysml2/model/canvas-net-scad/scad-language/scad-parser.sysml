package CanvasNet {
    part def ScadParser {
        doc /* The internal ScadParser (a sealed partial class with static Parse entry points over source text or a token list), the immutable syntax-tree records (ScadSyntax, ScadStatements, ScadExpressions), and the ScadTreeDepth verifier: a recursive-descent parser for statements and a precedence-climbing parser for expressions that is name-agnostic (every name(arguments) children statement is a module instantiation). It parses assignments, module and function definitions, instantiations with positional and named arguments, modifier characters, if/else, for, intersection_for, let, echo, and assert (as statements and expressions), literals, vectors, ranges, postfix index/member/call, function literals, the conditional and binary and unary operators with a documented precedence table, list comprehensions, and file-scope include/use directives, giving every node the location of its identifying token. It is fail-fast (the first error is one ScadSyntaxException), rejects nesting beyond 256 levels by a recursion counter with a stack-space guard and by an iterative post-parse tree-height check (ScadTreeDepth), and rejects source beyond 4,194,304 characters with an InvalidDataException. */

        comment sourceRef /* Source: src/DemaConsulting.CanvasNet.Scad/Language/ScadSyntax.cs, src/DemaConsulting.CanvasNet.Scad/Language/ScadStatements.cs, src/DemaConsulting.CanvasNet.Scad/Language/ScadExpressions.cs, src/DemaConsulting.CanvasNet.Scad/Language/ScadParser.cs, src/DemaConsulting.CanvasNet.Scad/Language/ScadParser.Statements.cs, src/DemaConsulting.CanvasNet.Scad/Language/ScadParser.Expressions.cs, src/DemaConsulting.CanvasNet.Scad/Language/ScadTreeDepth.cs */
        comment testRef /* Test: test/DemaConsulting.CanvasNet.Scad.Tests/Language/ScadParserStatementTests.cs, test/DemaConsulting.CanvasNet.Scad.Tests/Language/ScadParserControlFlowTests.cs, test/DemaConsulting.CanvasNet.Scad.Tests/Language/ScadParserExpressionTests.cs, test/DemaConsulting.CanvasNet.Scad.Tests/Language/ScadParserPrecedenceTests.cs, test/DemaConsulting.CanvasNet.Scad.Tests/Language/ScadParserComprehensionTests.cs, test/DemaConsulting.CanvasNet.Scad.Tests/Language/ScadParserErrorTests.cs, test/DemaConsulting.CanvasNet.Scad.Tests/Language/ScadParserLimitTests.cs, test/DemaConsulting.CanvasNet.Scad.Tests/Language/ScadParserNodeTests.cs, test/DemaConsulting.CanvasNet.Scad.Tests/Language/ScadParserTestSupport.cs, test/DemaConsulting.CanvasNet.Scad.Tests/Language/ScadAstDumper.cs */
        comment designRef /* Design: docs/design/canvas-net-scad/scad-language/scad-parser.md */
        comment verificationRef /* Verification: docs/verification/canvas-net-scad/scad-language/scad-parser.md */
        comment reqRef /* Requirements: docs/reqstream/canvas-net-scad/scad-language/scad-parser.yaml */
    }
}
