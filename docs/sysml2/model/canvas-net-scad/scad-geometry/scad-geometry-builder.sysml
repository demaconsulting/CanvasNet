package CanvasNet {
    part def ScadGeometryBuilder {
        /* cspell:ignore minkowski */
        doc /* The internal ScadGeometryBuilder engine (a sealed partial class) and its supporting types that convert the instantiation tree of an evaluation into a Render3D scene: an iterative post-order walk over an explicit stack (no recursion anywhere in the Geometry namespace, so any caller stack works), the implicit union of groups, loops, and user modules, dispatch tables for leaf, container, and unsupported modules (offset, surface, import, and roof are reported as scad-module-{name} and omitted, while a user module of the same name shadows the built-in; projection is built), the show-only modifier and the highlight and background overlays (a translucent ghost that is not part of the model and contributes no propagated bounds although it is part of the scene bounds that fit the default camera, and a translucent copy that shares its meshes and still takes part in the booleans, charged to the triangle budget; on a 2D shape that is not extruded they are reported), the position-preserving difference, the intersection, and the mixed 2D and 3D rules of the CSG booleans (ScadBooleans) with bounds for resize, the hull and minkowski convex combinations (ScadHulls: the exact hull of the points of 3D or 2D children, and the Minkowski sum of convex 3D children folded from the left with unions distributed, built on the Render3D ConvexHull and MinkowskiSum units, with the scad-hull-* and scad-minkowski-* reports for booleans, non-convex, mixed-dimension, degenerate, deferred 2D, and too-complex operands), the projection module (ScadProjections: the exact shadow of 3D children on the XY plane, as the union of the footprints of the upward faces with the silhouette of a difference or intersection classified exactly, and with cut = true their cross-section at z = 0 kept symbolic, as a 2D shape that every 2D consumer takes; reported as scad-projection-too-complex when the work ceiling is exceeded and as scad-projection-open-mesh when a section does not close, and charged to the triangle budget before allocation), top-level 2D shapes as slabs of the flat-shape thickness, a triangle budget charged before allocation (the exact count for primitives and extrusions; an upper bound of 2d - 4 for a hull and 2 * Va * Vb - 4 for each Minkowski sum, plus the transformed copies of the convex parts, settled to the exact count or refunded afterwards) and failing with a located ScadEvaluationException, cancellation polling, one reporting channel into the evaluation's sink with strict-mode ScadUnsupportedFeatureException and de-duplicated, file-aware locations, the map from mesh nodes to source locations, and the copy of the renderer options with a substituted handler and the render3d- to scad- feature identifier mapping. */

        comment sourceRef /* Source: src/DemaConsulting.CanvasNet.Scad/Geometry/ScadGeometryBuilder.cs, src/DemaConsulting.CanvasNet.Scad/Geometry/ScadGeometryBuilder.Anchors.cs, src/DemaConsulting.CanvasNet.Scad/Geometry/ScadGeometryBuilder.Walk.cs, src/DemaConsulting.CanvasNet.Scad/Geometry/ScadGeometryBuilder.Modifiers.cs, src/DemaConsulting.CanvasNet.Scad/Geometry/ScadGeometryBuilder.Unsupported.cs, src/DemaConsulting.CanvasNet.Scad/Geometry/ScadGeo.cs, src/DemaConsulting.CanvasNet.Scad/Geometry/ScadGeometryContext.cs, src/DemaConsulting.CanvasNet.Scad/Geometry/ScadSceneMap.cs, src/DemaConsulting.CanvasNet.Scad/Geometry/ScadReporter.cs, src/DemaConsulting.CanvasNet.Scad/Geometry/ScadSceneOptions.cs, src/DemaConsulting.CanvasNet.Scad/Geometry/ScadFeatureIds.cs, src/DemaConsulting.CanvasNet.Scad/Geometry/ScadBooleans.cs, src/DemaConsulting.CanvasNet.Scad/Geometry/ScadHulls.cs, src/DemaConsulting.CanvasNet.Scad/Geometry/ScadProjections.cs, src/DemaConsulting.CanvasNet.Scad/Geometry/ScadProjections.Classify.cs, src/DemaConsulting.CanvasNet.Scad/Geometry/ScadProjections.Faces.cs, src/DemaConsulting.CanvasNet.Scad/Geometry/ScadProjections.Slice.cs, src/DemaConsulting.CanvasNet.Scad/Geometry/ScadProjections.Tree.cs */
        comment testRef /* Test: test/DemaConsulting.CanvasNet.Scad.Tests/Geometry/ScadGeometryBuilderAnchorTests.cs, test/DemaConsulting.CanvasNet.Scad.Tests/Geometry/ScadGeometryBuilderWalkTests.cs, test/DemaConsulting.CanvasNet.Scad.Tests/Geometry/ScadGeometryBuilderModifierTests.cs, test/DemaConsulting.CanvasNet.Scad.Tests/Geometry/ScadGeometryBuilderStackTests.cs, test/DemaConsulting.CanvasNet.Scad.Tests/Geometry/ScadGeometryBuilderCancellationTests.cs, test/DemaConsulting.CanvasNet.Scad.Tests/Geometry/ScadGeometryBuilderLimitTests.cs, test/DemaConsulting.CanvasNet.Scad.Tests/Geometry/ScadGeometryBuilderBooleanTests.cs, test/DemaConsulting.CanvasNet.Scad.Tests/Geometry/ScadGeometryBuilderHullTests.cs, test/DemaConsulting.CanvasNet.Scad.Tests/Geometry/ScadGeometryBuilderMinkowskiTests.cs, test/DemaConsulting.CanvasNet.Scad.Tests/Geometry/ScadGeometryBuilderProjectionTests.cs, test/DemaConsulting.CanvasNet.Scad.Tests/Geometry/ScadGeometryBuilderProjectionCutTests.cs, test/DemaConsulting.CanvasNet.Scad.Tests/Geometry/ScadGeometryBuilderProjectionBudgetTests.cs, test/DemaConsulting.CanvasNet.Scad.Tests/Geometry/ScadProjectionTestSupport.cs, test/DemaConsulting.CanvasNet.Scad.Tests/Geometry/ScadGeometryBuilderTransformDepthTests.cs, test/DemaConsulting.CanvasNet.Scad.Tests/Geometry/ScadSceneOptionsTests.cs, test/DemaConsulting.CanvasNet.Scad.Tests/Geometry/ScadUnsupportedModuleTests.cs, test/DemaConsulting.CanvasNet.Scad.Tests/Geometry/ScadGeometryTestSupport.cs */
        comment designRef /* Design: docs/design/canvas-net-scad/scad-geometry/scad-geometry-builder.md */
        comment verificationRef /* Verification: docs/verification/canvas-net-scad/scad-geometry/scad-geometry-builder.md */
        comment reqRef /* Requirements: docs/reqstream/canvas-net-scad/scad-geometry/scad-geometry-builder.yaml */
    }
}
