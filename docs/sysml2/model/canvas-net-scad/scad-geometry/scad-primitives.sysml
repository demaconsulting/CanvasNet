package CanvasNet {
    part def ScadPrimitives {
        doc /* The internal ScadPrimitives static class (a partial class over three files), the ScadArguments binder, and the ScadFragmentRule formula, in the DemaConsulting.CanvasNet.Scad.Geometry namespace: they build the primitive shapes cube, sphere, cylinder, polyhedron, square, circle, and polygon from the evaluator's instances as Render3D meshes (solids) and polygon regions (2D shapes). Arguments are bound to each module's documented parameter names (positional order, named, special variables ignored, unknown, surplus, and duplicate arguments warned about, undef treated as absent), the fragment count follows the public $fn, $fa, and $fs formula with clamps, an invalid argument is a warning plus an empty result at the instance's location, a polygon the region checks reject is the unsupported feature scad-polygon-invalid, a polyhedron face that cannot be triangulated is scad-polyhedron-face-invalid (faces are reversed to counter-clockwise, a closed mesh of negative volume is reversed with a warning, and an open mesh is kept), any other tessellator rejection is scad-geometry-rejected, and the triangle budget is charged with the exact triangle count before allocation so a hostile fragment count fails with a located ScadEvaluationException. The unit contains no recursion. */

        comment sourceRef /* Source: src/DemaConsulting.CanvasNet.Scad/Geometry/ScadArguments.cs, src/DemaConsulting.CanvasNet.Scad/Geometry/ScadFragmentRule.cs, src/DemaConsulting.CanvasNet.Scad/Geometry/ScadPrimitives.cs, src/DemaConsulting.CanvasNet.Scad/Geometry/ScadPrimitives.Polyhedron.cs, src/DemaConsulting.CanvasNet.Scad/Geometry/ScadPrimitives.Shapes2D.cs */
        comment testRef /* Test: test/DemaConsulting.CanvasNet.Scad.Tests/Geometry/ScadArgumentsTests.cs, test/DemaConsulting.CanvasNet.Scad.Tests/Geometry/ScadFragmentRuleTests.cs, test/DemaConsulting.CanvasNet.Scad.Tests/Geometry/ScadPrimitivesSolidTests.cs, test/DemaConsulting.CanvasNet.Scad.Tests/Geometry/ScadPrimitivesShape2DTests.cs, test/DemaConsulting.CanvasNet.Scad.Tests/Geometry/ScadPolyhedronTests.cs, test/DemaConsulting.CanvasNet.Scad.Tests/Geometry/ScadGeometryTestSupport.cs */
        comment designRef /* Design: docs/design/canvas-net-scad/scad-geometry/scad-primitives.md */
        comment verificationRef /* Verification: docs/verification/canvas-net-scad/scad-geometry/scad-primitives.md */
        comment reqRef /* Requirements: docs/reqstream/canvas-net-scad/scad-geometry/scad-primitives.yaml */
    }
}
