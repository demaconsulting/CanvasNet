package CanvasNet {
    part def ScadExtrusions {
        doc /* The internal ScadExtrusions static class and the symbolic ScadShape2D tree it works on: the package has no 2D boolean kernel, so a 2D result is a tree of regions, planar transforms, colors, and booleans, and linear_extrude, rotate_extrude, and the slabs of top-level 2D shapes are distributed over that tree - the planar matrices are applied to the points of every leaf first, each leaf is extruded with parameters (slice or segment count) shared across the leaves, and the tree is rebuilt as a 3D scene tree so that the extrusion of a difference is the difference of the extrusions. linear_extrude has a default height of 100, centering, an ignored convexity, a twist that is positive clockwise seen from +Z, a scalar, vector, or apex scale, and a default slice rule; rotate_extrude has a default angle of 360, clamps larger angles, sweeps negative angles clockwise, sweeps a profile at x <= 0 where it lies (a point at (-4, 0) with a 90 degree angle sweeps from 180 to 270 degrees), chooses its segment count by the fragment rule while keeping every angular step within the 120 degrees the renderer's extruder accepts, and reports axis crossings and isolated axis contacts. Invalid arguments are warnings, unsupported scales and axis problems are unsupported features that omit the whole extrusion, any other renderer rejection is scad-geometry-rejected, the exact triangle count (caps of V + 2H - 2P triangles) is checked against the budget (with saturating arithmetic) before allocation and reconciled with the mesh, and every walk over a tree is iterative. */

        comment sourceRef /* Source: src/DemaConsulting.CanvasNet.Scad/Geometry/ScadShape2D.cs, src/DemaConsulting.CanvasNet.Scad/Geometry/ScadExtrusions.cs, src/DemaConsulting.CanvasNet.Scad/Geometry/ScadExtrusions.Linear.cs, src/DemaConsulting.CanvasNet.Scad/Geometry/ScadExtrusions.Rotate.cs */
        comment testRef /* Test: test/DemaConsulting.CanvasNet.Scad.Tests/Geometry/ScadExtrusionsLinearTests.cs, test/DemaConsulting.CanvasNet.Scad.Tests/Geometry/ScadExtrusionsRotateTests.cs, test/DemaConsulting.CanvasNet.Scad.Tests/Geometry/ScadExtrusionsMappingTests.cs, test/DemaConsulting.CanvasNet.Scad.Tests/Geometry/ScadGeometryTestSupport.cs */
        comment designRef /* Design: docs/design/canvas-net-scad/scad-geometry/scad-extrusions.md */
        comment verificationRef /* Verification: docs/verification/canvas-net-scad/scad-geometry/scad-extrusions.md */
        comment reqRef /* Requirements: docs/reqstream/canvas-net-scad/scad-geometry/scad-extrusions.yaml */
    }
}
