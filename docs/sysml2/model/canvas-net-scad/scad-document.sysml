package CanvasNet {
    part def ScadDocument {
        doc /* The public API of CanvasNetScad in the DemaConsulting.CanvasNet.Scad namespace: the sealed, immutable, thread-safe ScadDocument with the static Parse(string), Open(string path), and Open(Stream) entry points (UTF-8 with byte-order-mark detection, source limited to 4,194,304 characters, the stream left open and a non-terminating stream bounded), the SourceName, Directives (file-scope include/use directives in source order, recorded and never resolved while parsing), ModuleNames, and FunctionNames (file-scope definitions in source order, duplicates kept) properties, the Evaluate method that evaluates the document headlessly and returns a ScadEvaluationResult (echo lines, diagnostics, unsupported-feature reports, instance count), the BuildScene method that evaluates the document (with the viewport variables that follow from the camera and the view angles of the render options; an explicit camera that the renderer would reject defines none of them and does not make the method throw) and builds a Render3D Scene of its geometry, and the Render method that draws that scene onto a new Surface (a fitted view by default - isometric, or a flat top-down view for a model that is entirely 2D - or a caller-supplied camera; invalid size or camera rejected before any evaluation; events of all stages delivered once, in order, on the calling thread; cancellation honored; byte-identical images from repeated and concurrent calls), the viewport special variables $vpt, $vpr, $vpd, and $vpf (defined for every model with the values of the view that is drawn, read back from the model's top-level assignments, and applied with the precedence explicit render options, then variable overrides, then assignments, then defaults, an assigned $vpr alone steering a fitted view and an assigned $vpt, $vpd, or $vpf selecting a manual camera) and the choice of the camera that follows from them; the immutable, validated ScadOpenOptions (BaseDirectory, LibraryPaths, FileResolver, SourceName), ScadEvaluationOptions (Variables, Time, Limits, handlers, ThrowOnUnsupportedFeature), and ScadRenderOptions (Evaluation, Camera, ViewAzimuthDegrees, ViewElevationDegrees, Projection, SceneOptions, FlatShapeThickness, HighlightColor, GhostColor, FontResolution, ResolvedViewHandler) with the ScadResolvedView record and ScadViewSource enumeration that report the view that was drawn and ScadFontResolutionOptions (UseSystemFonts, AdditionalDirectories: where an explicitly named text font is found); the ScadLimits resource limits, including the MaxTriangles limit on generated geometry; the ScadSourceLocation record struct (file, one-based line and column); the ScadSyntaxException (a FormatException carrying the Location of the first syntax error), the ScadEvaluationException (an InvalidOperationException carrying the Location of a failed evaluation), and the ScadUnsupportedFeatureException (an IOException carrying the feature and location); the ScadDiagnostic and ScadUnsupportedFeature records; and the ScadDirective record with its ScadDirectiveKind enumeration. It delegates all lexing and parsing to the internal ScadLanguage subsystem, all evaluation to the internal ScadEvaluation subsystem, and all geometry building to the internal ScadGeometry subsystem and the Render3D renderer, and opens no file while parsing. The unit also covers ScadImageSource (the IImageSource for .scad files: the view the library chooses for the model (isometric for 3D, top-down for a flat 2D model, or the model's own $vp* variables) at the placement size over a transparent background, includes resolved in the folder of the request, notes and echo returned) for the shared image resolver of the core ImageSources subsystem. The ScadImageSource declares the fragment prefix def. (IFragmentImageSource): every def.name=value of a link sets a variable of the model through ScadEvaluationOptions.Variables like -D of the tool, and an unusable value or name refuses the link with image-fragment-invalid. */

        comment sourceRef /* Source: src/DemaConsulting.CanvasNet.Scad/ScadAnchor.cs, src/DemaConsulting.CanvasNet.Scad/ScadImageSource.cs, src/DemaConsulting.CanvasNet.Scad/ScadDocument.cs, src/DemaConsulting.CanvasNet.Scad/ScadOpenOptions.cs, src/DemaConsulting.CanvasNet.Scad/ScadSourceLocation.cs, src/DemaConsulting.CanvasNet.Scad/ScadSyntaxException.cs, src/DemaConsulting.CanvasNet.Scad/ScadDirective.cs, src/DemaConsulting.CanvasNet.Scad/ScadDirectiveKind.cs, src/DemaConsulting.CanvasNet.Scad/ScadDocument.Evaluate.cs, src/DemaConsulting.CanvasNet.Scad/ScadDocument.Render.cs, src/DemaConsulting.CanvasNet.Scad/ScadRenderOptions.cs, src/DemaConsulting.CanvasNet.Scad/ScadFontResolutionOptions.cs, src/DemaConsulting.CanvasNet.Scad/ScadViewport.cs, src/DemaConsulting.CanvasNet.Scad/ScadResolvedView.cs, src/DemaConsulting.CanvasNet.Scad/ScadViewSource.cs, src/DemaConsulting.CanvasNet.Scad/ScadEvaluationOptions.cs, src/DemaConsulting.CanvasNet.Scad/ScadEvaluationResult.cs, src/DemaConsulting.CanvasNet.Scad/ScadLimits.cs, src/DemaConsulting.CanvasNet.Scad/ScadDiagnostic.cs, src/DemaConsulting.CanvasNet.Scad/ScadUnsupportedFeature.cs, src/DemaConsulting.CanvasNet.Scad/ScadUnsupportedFeatureException.cs, src/DemaConsulting.CanvasNet.Scad/ScadEvaluationException.cs, src/DemaConsulting.CanvasNet.Scad/NamespaceDoc.cs */
        comment testRef /* Test: test/DemaConsulting.CanvasNet.Scad.Tests/ScadAnchorTests.cs, test/DemaConsulting.CanvasNet.Scad.Tests/ScadDocumentAnchorTests.cs, test/DemaConsulting.CanvasNet.Scad.Tests/ScadImageSourceTests.cs, test/DemaConsulting.CanvasNet.Scad.Tests/ScadImageSourceDefineTests.cs, test/DemaConsulting.CanvasNet.Scad.Tests/ScadDocumentTests.cs, test/DemaConsulting.CanvasNet.Scad.Tests/ScadOpenOptionsTests.cs, test/DemaConsulting.CanvasNet.Scad.Tests/ScadSourceLocationTests.cs, test/DemaConsulting.CanvasNet.Scad.Tests/ScadSyntaxExceptionTests.cs, test/DemaConsulting.CanvasNet.Scad.Tests/ScadDocumentEvaluateTests.cs, test/DemaConsulting.CanvasNet.Scad.Tests/ScadDocumentEvaluateSafetyTests.cs, test/DemaConsulting.CanvasNet.Scad.Tests/ScadRenderOptionsTests.cs, test/DemaConsulting.CanvasNet.Scad.Tests/ScadDocumentBuildSceneTests.cs, test/DemaConsulting.CanvasNet.Scad.Tests/ScadDocumentRenderTests.cs, test/DemaConsulting.CanvasNet.Scad.Tests/ScadDocumentRenderCsgTests.cs, test/DemaConsulting.CanvasNet.Scad.Tests/ScadDocumentRenderExtrusionTests.cs, test/DemaConsulting.CanvasNet.Scad.Tests/ScadDocumentRenderReportTests.cs, test/DemaConsulting.CanvasNet.Scad.Tests/ScadViewportTests.cs, test/DemaConsulting.CanvasNet.Scad.Tests/ScadDocumentViewportRenderTests.cs, test/DemaConsulting.CanvasNet.Scad.Tests/ScadEvaluationOptionsTests.cs, test/DemaConsulting.CanvasNet.Scad.Tests/ScadLimitsTests.cs, test/DemaConsulting.CanvasNet.Scad.Tests/ScadDiagnosticTests.cs, test/DemaConsulting.CanvasNet.Scad.Tests/ScadUnsupportedFeatureTests.cs, test/DemaConsulting.CanvasNet.Scad.Tests/ScadEvaluationExceptionTests.cs, test/DemaConsulting.CanvasNet.Scad.Tests/ScadFixtureEvaluationTests.cs, test/DemaConsulting.CanvasNet.Scad.Tests/ScadFixtures/ */
        comment designRef /* Design: docs/design/canvas-net-scad/scad-document.md */
        comment verificationRef /* Verification: docs/verification/canvas-net-scad/scad-document.md */
        comment reqRef /* Requirements: docs/reqstream/canvas-net-scad/scad-document.yaml */
    }
}
