package CanvasNet {
    part def ScadBuiltinFunctions {
        doc /* The internal ScadBuiltinFunctions static class and its host interface: a frozen registry of built-in functions with positional and named argument binding - mathematics (abs, sign, sqrt, exp, ln, log, floor, ceil, round, pow, min, max), degree-based trigonometry that is exact at multiples of ninety degrees, vector and list functions (len, concat, norm, cross, lookup, search), string functions (str, chr, ord), type tests, version, and rands backed by the platform-independent SplitMix64 ScadRandom - plus the reporting of recognized but unsupported functions as unsupported features. Functions return undef with a warning for wrong arguments, check list and string limits before building a result, and charge the evaluation budget for work proportional to their input through the IScadBuiltinHost. */

        comment sourceRef /* Source: src/DemaConsulting.CanvasNet.Scad/Evaluation/IScadBuiltinHost.cs, src/DemaConsulting.CanvasNet.Scad/Evaluation/ScadBuiltinFunctions.cs, src/DemaConsulting.CanvasNet.Scad/Evaluation/ScadBuiltinFunctions.Math.cs, src/DemaConsulting.CanvasNet.Scad/Evaluation/ScadBuiltinFunctions.Lists.cs, src/DemaConsulting.CanvasNet.Scad/Evaluation/ScadBuiltinFunctions.Search.cs, src/DemaConsulting.CanvasNet.Scad/Evaluation/ScadBuiltinFunctions.Strings.cs, src/DemaConsulting.CanvasNet.Scad/Evaluation/ScadBuiltinFunctions.Types.cs, src/DemaConsulting.CanvasNet.Scad/Evaluation/ScadBuiltinFunctions.Random.cs, src/DemaConsulting.CanvasNet.Scad/Evaluation/ScadRandom.cs */
        comment testRef /* Test: test/DemaConsulting.CanvasNet.Scad.Tests/Evaluation/ScadBuiltinMathTests.cs, test/DemaConsulting.CanvasNet.Scad.Tests/Evaluation/ScadBuiltinListTests.cs, test/DemaConsulting.CanvasNet.Scad.Tests/Evaluation/ScadBuiltinSearchLimitTests.cs, test/DemaConsulting.CanvasNet.Scad.Tests/Evaluation/ScadBuiltinStringTests.cs, test/DemaConsulting.CanvasNet.Scad.Tests/Evaluation/ScadBuiltinRandomTests.cs, test/DemaConsulting.CanvasNet.Scad.Tests/Evaluation/ScadBuiltinRegistryTests.cs, test/DemaConsulting.CanvasNet.Scad.Tests/Evaluation/ScadTestBuiltinHost.cs */
        comment designRef /* Design: docs/design/canvas-net-scad/scad-evaluation/scad-builtin-functions.md */
        comment verificationRef /* Verification: docs/verification/canvas-net-scad/scad-evaluation/scad-builtin-functions.md */
        comment reqRef /* Requirements: docs/reqstream/canvas-net-scad/scad-evaluation/scad-builtin-functions.yaml */
    }
}
