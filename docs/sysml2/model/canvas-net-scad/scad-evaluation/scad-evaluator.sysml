package CanvasNet {
    part def ScadEvaluator {
        doc /* The internal ScadEvaluator (a sealed partial class with a static, restartable Evaluate entry point) that evaluates a resolved, include-expanded program into a geometry-agnostic instantiation tree: lazily evaluated, last-assignment-wins scopes (ScadScope), dynamically scoped special variables, user functions, closures and tail calls, user modules with children, conditionals, loops, ranges, list comprehensions, operators, echo and assert, include/use imports, caller-supplied variable overrides, the viewport special variables $vpt, $vpr, $vpd, and $vpf (defined in the defaults scope from the viewport values of the evaluation settings, and read back after evaluation as the ScadDocumentViewport of the output: the top-level assignments of the main file and its includes, validated with one warning for an invalid value), and the immutable ScadInstance tree (built-in module nodes and groups, with evaluated arguments, modifiers, fragment settings, and locations) that the later geometry phase consumes without access to the syntax tree. It buffers every echo line, warning, and unsupported-feature report in the ScadEvaluationSink (de-duplicated, capped, resettable, replayed in order), counts frames, steps (vector operands by their saturated, capped, memoized logical element count), loop iterations, instances, and output against ScadLimits, polls cancellation, and enforces the recursion limit with a deterministic frame counter: the pass runs inline on the caller's thread guarded by the runtime stack check and, only when that guard trips, is discarded and restarted on a bounded, dedicated 384 MiB-stack thread. */

        comment sourceRef /* Source: src/DemaConsulting.CanvasNet.Scad/Evaluation/ScadEvaluator.cs, src/DemaConsulting.CanvasNet.Scad/Evaluation/ScadEvaluator.Scopes.cs, src/DemaConsulting.CanvasNet.Scad/Evaluation/ScadEvaluator.Expressions.cs, src/DemaConsulting.CanvasNet.Scad/Evaluation/ScadEvaluator.Calls.cs, src/DemaConsulting.CanvasNet.Scad/Evaluation/ScadEvaluator.Statements.cs, src/DemaConsulting.CanvasNet.Scad/Evaluation/ScadEvaluator.Modules.cs, src/DemaConsulting.CanvasNet.Scad/Evaluation/ScadEvaluator.Comprehensions.cs, src/DemaConsulting.CanvasNet.Scad/Evaluation/ScadEvaluator.Host.cs, src/DemaConsulting.CanvasNet.Scad/Evaluation/ScadEvaluatorElementCounter.cs, src/DemaConsulting.CanvasNet.Scad/Evaluation/ScadEvaluatorFallbackSlots.cs, src/DemaConsulting.CanvasNet.Scad/Evaluation/ScadScope.cs, src/DemaConsulting.CanvasNet.Scad/Evaluation/ScadInstance.cs, src/DemaConsulting.CanvasNet.Scad/Evaluation/ScadBuiltinModules.cs, src/DemaConsulting.CanvasNet.Scad/Evaluation/ScadEvaluationSettings.cs, src/DemaConsulting.CanvasNet.Scad/Evaluation/ScadEvaluationOutput.cs, src/DemaConsulting.CanvasNet.Scad/Evaluation/ScadViewportValues.cs, src/DemaConsulting.CanvasNet.Scad/Evaluation/ScadEvaluationSink.cs */
        comment testRef /* Test: test/DemaConsulting.CanvasNet.Scad.Tests/Evaluation/ScadEvaluatorAnchorTests.cs, test/DemaConsulting.CanvasNet.Scad.Tests/Evaluation/ScadEvaluatorScopingTests.cs, test/DemaConsulting.CanvasNet.Scad.Tests/Evaluation/ScadEvaluatorSpecialVariableTests.cs, test/DemaConsulting.CanvasNet.Scad.Tests/Evaluation/ScadEvaluatorViewportTests.cs, test/DemaConsulting.CanvasNet.Scad.Tests/Evaluation/ScadEvaluatorFunctionTests.cs, test/DemaConsulting.CanvasNet.Scad.Tests/Evaluation/ScadEvaluatorTailCallTests.cs, test/DemaConsulting.CanvasNet.Scad.Tests/Evaluation/ScadEvaluatorModuleTests.cs, test/DemaConsulting.CanvasNet.Scad.Tests/Evaluation/ScadEvaluatorControlFlowTests.cs, test/DemaConsulting.CanvasNet.Scad.Tests/Evaluation/ScadEvaluatorComprehensionTests.cs, test/DemaConsulting.CanvasNet.Scad.Tests/Evaluation/ScadEvaluatorExpressionTests.cs, test/DemaConsulting.CanvasNet.Scad.Tests/Evaluation/ScadEvaluatorInstanceTreeTests.cs, test/DemaConsulting.CanvasNet.Scad.Tests/Evaluation/ScadEvaluatorIncludeUseTests.cs, test/DemaConsulting.CanvasNet.Scad.Tests/Evaluation/ScadEvaluatorOverrideTests.cs, test/DemaConsulting.CanvasNet.Scad.Tests/Evaluation/ScadEvaluatorDiagnosticsTests.cs, test/DemaConsulting.CanvasNet.Scad.Tests/Evaluation/ScadEvaluatorLimitTests.cs, test/DemaConsulting.CanvasNet.Scad.Tests/Evaluation/ScadEvaluatorProductLimitTests.cs, test/DemaConsulting.CanvasNet.Scad.Tests/Evaluation/ScadEvaluatorAggregateLimitTests.cs, test/DemaConsulting.CanvasNet.Scad.Tests/Evaluation/ScadEvaluatorElementCounterTests.cs, test/DemaConsulting.CanvasNet.Scad.Tests/Evaluation/ScadEvaluatorStackTests.cs, test/DemaConsulting.CanvasNet.Scad.Tests/Evaluation/ScadEvaluatorCancellationTests.cs, test/DemaConsulting.CanvasNet.Scad.Tests/Evaluation/ScadEvaluatorDeterminismTests.cs, test/DemaConsulting.CanvasNet.Scad.Tests/Evaluation/ScadEvaluatorCultureTests.cs, test/DemaConsulting.CanvasNet.Scad.Tests/Evaluation/ScadEvaluatorEntryPointTests.cs, test/DemaConsulting.CanvasNet.Scad.Tests/Evaluation/ScadEvaluatorFixtureTests.cs, test/DemaConsulting.CanvasNet.Scad.Tests/Evaluation/ScadEvaluationSinkTests.cs, test/DemaConsulting.CanvasNet.Scad.Tests/Evaluation/ScadEvaluatorTestSupport.cs */
        comment designRef /* Design: docs/design/canvas-net-scad/scad-evaluation/scad-evaluator.md */
        comment verificationRef /* Verification: docs/verification/canvas-net-scad/scad-evaluation/scad-evaluator.md */
        comment reqRef /* Requirements: docs/reqstream/canvas-net-scad/scad-evaluation/scad-evaluator.yaml */
    }
}
