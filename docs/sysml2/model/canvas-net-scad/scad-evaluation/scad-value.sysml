package CanvasNet {
    part def ScadValue {
        doc /* The internal value model of the evaluator: the immutable ScadValue struct (undef, boolean, number, string, vector, range, and function values) with its truthiness, equality, ordering, arithmetic (numbers, element-wise vectors, scaling, dot product, and matrix products), indexing and member access (Unicode-scalar string indexing), string and echo text forms, and conversion from caller-supplied objects; the ScadVector and lazily-measured ScadRange value types; the culture-independent six-significant-digit ScadNumberFormatter; the IEEE ScadNumbers equality helper; and the Unicode-scalar ScadText helpers. Recursive operations are guarded against stack exhaustion and values are limited to 256 nesting levels by the constructs that build them. */

        comment sourceRef /* Source: src/DemaConsulting.CanvasNet.Scad/Evaluation/ScadValueKind.cs, src/DemaConsulting.CanvasNet.Scad/Evaluation/ScadValue.cs, src/DemaConsulting.CanvasNet.Scad/Evaluation/ScadValue.Compare.cs, src/DemaConsulting.CanvasNet.Scad/Evaluation/ScadValue.Arithmetic.cs, src/DemaConsulting.CanvasNet.Scad/Evaluation/ScadValue.Matrix.cs, src/DemaConsulting.CanvasNet.Scad/Evaluation/ScadValue.Format.cs, src/DemaConsulting.CanvasNet.Scad/Evaluation/ScadValue.Convert.cs, src/DemaConsulting.CanvasNet.Scad/Evaluation/ScadVector.cs, src/DemaConsulting.CanvasNet.Scad/Evaluation/ScadRange.cs, src/DemaConsulting.CanvasNet.Scad/Evaluation/IScadFunctionValue.cs, src/DemaConsulting.CanvasNet.Scad/Evaluation/ScadNumberFormatter.cs, src/DemaConsulting.CanvasNet.Scad/Evaluation/ScadNumbers.cs, src/DemaConsulting.CanvasNet.Scad/Evaluation/ScadText.cs */
        comment testRef /* Test: test/DemaConsulting.CanvasNet.Scad.Tests/Evaluation/ScadValueTests.cs, test/DemaConsulting.CanvasNet.Scad.Tests/Evaluation/ScadValueArithmeticTests.cs, test/DemaConsulting.CanvasNet.Scad.Tests/Evaluation/ScadValueProductLimitTests.cs, test/DemaConsulting.CanvasNet.Scad.Tests/Evaluation/ScadValueFormatTests.cs, test/DemaConsulting.CanvasNet.Scad.Tests/Evaluation/ScadValueConversionTests.cs, test/DemaConsulting.CanvasNet.Scad.Tests/Evaluation/ScadValueNestingTests.cs, test/DemaConsulting.CanvasNet.Scad.Tests/Evaluation/ScadNumberFormatterTests.cs, test/DemaConsulting.CanvasNet.Scad.Tests/Evaluation/ScadRangeTests.cs, test/DemaConsulting.CanvasNet.Scad.Tests/Evaluation/ScadTextTests.cs */
        comment designRef /* Design: docs/design/canvas-net-scad/scad-evaluation/scad-value.md */
        comment verificationRef /* Verification: docs/verification/canvas-net-scad/scad-evaluation/scad-value.md */
        comment reqRef /* Requirements: docs/reqstream/canvas-net-scad/scad-evaluation/scad-value.yaml */
    }
}
