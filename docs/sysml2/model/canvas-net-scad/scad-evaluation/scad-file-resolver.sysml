package CanvasNet {
    part def ScadFileResolver {
        doc /* The internal ScadFileResolver (a sealed partial class) and the immutable ScadSourceUnit it produces: before any evaluation it expands include directives textually (keeping each statement's own source location) and loads use directives as separate, private library units, reading every file through the core FileReferenceResolver under the file-access policy of ScadOpenOptions.FileAccess (AllowAll by default, like OpenSCAD itself: dot-dot, absolute and drive paths and symbolic links are followed) - the including file's directory, the base directory and the library paths in file-system mode (search locations, not boundaries), or normalized logical paths handed to the caller's resolver callback with no file-system access and no policy at all, where dot-dot above the root and absolute paths are errors - rejecting control characters (C0 and C1), network, device and alternate-data-stream paths under every policy, treating a denial of the policy, a file whose real path a restrictive policy cannot determine, a non-regular file (a directory in place of a file), a file that cannot be opened and a throwing callback as located errors, a dangling link as a missing file, and never consulting environment variables. This unit adds the search context (the including file's directory, then the library paths), include cycles (compared on the real path of the file, so a file reached again through a link or another spelling is a cycle; libraries are cached by real path), bounds on include depth, included files, and expanded statements, the bounded UTF-8 decoding with byte-order-mark detection and the source-length limit, one parse per distinct path, the file names used in locations, and the OpenSCAD wording and location of every refusal (Translate maps all eleven FileReferenceFailureKind values; a denial is "Include file '...' was denied by the file-access policy '...': reason", whose InnerException is the FileReferenceException, and the shown name is relative to the base directory or as written, never a host directory the author did not write); it reports a missing file as a warning, lets syntax errors in referenced files surface with that file's name, and polls cancellation between files. */

        comment sourceRef /* Source: src/DemaConsulting.CanvasNet.Scad/Evaluation/ScadSourceUnit.cs, src/DemaConsulting.CanvasNet.Scad/Evaluation/ScadFileResolver.cs, src/DemaConsulting.CanvasNet.Scad/Evaluation/ScadFileResolver.Paths.cs */
        comment testRef /* Test: test/DemaConsulting.CanvasNet.Scad.Tests/Evaluation/ScadFileResolverIncludeTests.cs, test/DemaConsulting.CanvasNet.Scad.Tests/Evaluation/ScadFileResolverUseTests.cs, test/DemaConsulting.CanvasNet.Scad.Tests/Evaluation/ScadFileResolverSandboxTests.cs, test/DemaConsulting.CanvasNet.Scad.Tests/Evaluation/ScadFileResolverLinkTests.cs, test/DemaConsulting.CanvasNet.Scad.Tests/Evaluation/ScadFileResolverLimitTests.cs, test/DemaConsulting.CanvasNet.Scad.Tests/Evaluation/ScadFileResolverFileSystemTests.cs, test/DemaConsulting.CanvasNet.Scad.Tests/Evaluation/ScadResolverTestSupport.cs */
        comment designRef /* Design: docs/design/canvas-net-scad/scad-evaluation/scad-file-resolver.md */
        comment verificationRef /* Verification: docs/verification/canvas-net-scad/scad-evaluation/scad-file-resolver.md */
        comment reqRef /* Requirements: docs/reqstream/canvas-net-scad/scad-evaluation/scad-file-resolver.yaml */
    }
}
