package CanvasNet {
    part def CanvasNetViewer {
        doc /* The static class that lists the built-in image sources (raster, SVG, PDF, PPTX, VSDX, OpenSCAD, Vega-Lite, and Mermaid, in a fixed order; adapters over the SourceLoader of the Imaging subsystem, so a linked file and a rendered file are drawn by the same code as the canvasnet tool) and the extensions they claim, creates a new FolderImageResolver for one render (with optional extra sources placed after the built-in ones, so the later source wins), and renders any file by path or from a stream as a ViewerImage that owns the picture and carries the format, the page drawn and the page count, the notes (with detail, location, and origin), the printed text, the anchors of a model, and the embedded images. A document link chooses its page, slide, or model view, and a diagram link its theme, with the fragment of the link (page=N, slide=N, view=name, theme=name; page 1 without one). ViewerRenderOptions carries the requested size, the page, the resolution, the background, the model options, the base folder of the links (a base, not a boundary), the file-access policy (FileAccess, AllowAll by default like Pandoc, null refused, passed to the resolver and so to every nested picture, model include, and chart data file), the strictness switch, extra sources, and a cancellation token. The file a caller renders by path may lie anywhere (also outside Folder or behind a link) and is never judged by the policy; a non-regular, too large, or unreadable file is a FileReferenceException. A link the policy denies is the warning image-access-denied, and with ThrowOnUnsupportedFeature the ViewerException file-access-denied (ErrorCodes.FileAccessDenied). A vector file is drawn at the requested size, a raster is fitted or scaled by the viewer. The class is static and stateless, and every call builds its own resolver. The built-in sources declare the prefixes def. (a model) and param. (a chart) and set the variables of a model and the parameters of a chart from the fragment of a link, and ViewerRenderOptions.VegaLite (ChartOptions) sets the parameters of a chart that is rendered directly, so the command line, the library and an embedded file draw a parameterized chart the same way. */

        comment sourceRef /* Source: src/DemaConsulting.CanvasNet.Viewer/CanvasNetViewer.cs, src/DemaConsulting.CanvasNet.Viewer/LoaderImageSource.cs, src/DemaConsulting.CanvasNet.Viewer/ViewerRenderOptions.cs, src/DemaConsulting.CanvasNet.Viewer/ViewerImage.cs, src/DemaConsulting.CanvasNet.Viewer/NamespaceDoc.cs */
        comment testRef /* Test: test/DemaConsulting.CanvasNet.Viewer.Tests/CanvasNetViewerTests.cs, test/DemaConsulting.CanvasNet.Viewer.Tests/CanvasNetViewerSystemIntegrationTests.cs, test/DemaConsulting.CanvasNet.Viewer.Tests/CanvasNetViewerFragmentTests.cs, test/DemaConsulting.CanvasNet.Viewer.Tests/CanvasNetViewerParameterFragmentTests.cs, test/DemaConsulting.CanvasNet.Viewer.Tests/CanvasNetViewerRenderOptionsTests.cs, test/DemaConsulting.CanvasNet.Viewer.Tests/ViewerFixtures.cs */
        comment designRef /* Design: docs/design/canvas-net-viewer/canvas-net-viewer.md */
        comment verificationRef /* Verification: docs/verification/canvas-net-viewer/canvas-net-viewer.md */
        comment reqRef /* Requirements: docs/reqstream/canvas-net-viewer/canvas-net-viewer.yaml */
    }
}
