package CanvasNet {
    part def SourceLoader {
        doc /* Turns a path into facts or into pixels for the files the tool reads. Detect recognizes the format from the signature bytes, then the entries of a ZIP package (presentation or drawing), then SVG text, then the extension (a file named .scad is a model); a file named .vl.json or .vl, or a .json file whose top-level $schema property names a Vega-Lite schema (read from the first 4 KiB), is a Vega-Lite chart (never taken for an SVG; a plain Vega specification is an unsupported format); a file named .mmd or .mermaid is a Mermaid diagram (never taken for an SVG, and never recognized by its content); Probe reads the header facts (Probe(path) and Probe(InputReference) read the files a chart is measured with under the default policy, the overloads Probe(path, FileAccessPolicy) and Probe(InputReference, FileAccessPolicy) under the caller's, and Load(path, options) probes with options.FileAccess, so a probe never reads a data file the load would refuse; format, size, channels, transparency, decodability, frame count, EXIF orientation, for a PDF, PPTX, or VSDX document every page with its size, rotation, and name, for an OpenSCAD model, by parsing it, the names of its modules and functions and its include and use directives, for a Vega-Lite chart, by parsing and measuring it, the laid-out size and its marks, data references, parameters, title, and schema version, and for a Mermaid diagram, by parsing and measuring it without its pictures, the laid-out size and, as DiagramFacts, its type, whether this version draws it, its direction, titles, and numbers of nodes, edges, and subgraphs) without decoding; Load and OpenPages decode a raster at its own size, render an SVG directly at the target size (an image element of an SVG file that names a file (relative to the SVG file, or absolute) - a raster, an SVG file, an OpenSCAD model, a Vega-Lite chart, or a page of a document (page 1, or the page the fragment of the link names) - is loaded by the image resolver that CanvasNetViewer.CreateImageResolver creates for the folder of the SVG file and that this unit hands to the SVG library through SvgLoadOptions.ImageResolver under SourceOptions.FileAccess (AllowAll by default, like Pandoc); the file-access policy, the limits, the dispatch by file name extension (the extensions of CanvasNetViewer.Extensions, documented in the svg help topic), and the nesting belong to the core ImageSources subsystem, and this unit only maps what the resolver reports to its own notes, text, and embed operations, turns an unresolved reference into an unsupported-feature error when strict (a reference the policy denied, the warning image-access-denied, into file-access-denied), maps the failure of a file that is found but cannot be drawn to the error code of that failure naming both files, and keeps the tool free of any plug-in mechanism), render a chosen page of a document at a resolution (opening the document once for all its pages), or draw an OpenSCAD model from a named view (iso, front, back, left, right, top, or bottom, with the azimuth and elevation replaceable, orthographic or perspective; the view is passed to the SCAD library only when a view name, azimuth, or elevation is given, so that otherwise the library chooses it - iso for a model with 3D objects, top for a model that is entirely 2D, or the model's own $vpr view - and the view it used is reported in the operation) at 800 by 800 pixels by default with variables, time, default color, and a triangle limit applied and with its include and use files looked up relative to the file that names them and read under SourceOptions.FileAccess (a missing one is scad-error, a denied one file-access-denied), or draw a Vega-Lite chart at its laid-out size or the size asked for over its own background (UTC dates, bundled fonts only, no network, and the data files of the chart read by the library relative to the folder of the specification under SourceOptions.FileAccess, with no data-folder option), or draw a Mermaid diagram (SourceLoader.Mermaid.cs) at its laid-out size times the scale, placed exactly as Mermaid places it, or fitted into the box the width and height ask for, over white or the background given, in the theme of SourceOptions.Mermaid (DiagramOptions; a theme fragment of the input replaces it and a theme the text sets wins over both), with the warnings of the library as mermaid-warning notes, the constructs it does not draw (including a diagram type that is not drawn, an empty picture) as unsupported notes or, when strict, an unsupported-feature error, and the pictures of its nodes drawn through the same SvgImages resolver as the pictures of a chart, each embed operation listed once, applying the size policy (scale, width, height, fitting a page inside a box, rounding, the 8192-pixel limit before decoding), the EXIF orientation of a JPEG (read by the core JpegCodec and applied by the core Surface), and the background color, collecting the notes about skipped or approximated features and the warnings and echo of a model (or refusing the features when strict), and reporting the operations applied. It reads a file through a SourceInput (a file on disk or bytes in memory, with the folder and name that the files a format names itself are looked up in) and a LoadContext (hooks that charge each surface to a pixel budget before it is allocated, a cancellation token, a scoped resolver for the nested pictures of an SVG file, and fitted-page output), so the CanvasNetViewer adapters draw an embedded file with the same code as the tool; it checks the SourceOptions of Load and OpenPages before any file is touched (ranges equal to the command line, MaxDpi 2400; a violation is a usage-error); and it reports with each note of a model or chart the finer identifier of the library as Detail and the position in the file as Location. It maps an explicit list of library exceptions (missing, unreadable, unsupported feature, corrupt data, SCAD syntax and evaluation errors, Vega-Lite specification and render errors, Mermaid syntax and render errors - mermaid-error, or budget-exceeded for a limit of the library - - a local data file that is missing or not valid is a vega-lite-error, a data limit is budget-exceeded, and a data file or include the file-access policy denies (a FileReferenceException of kind AccessDenied or RealPathUnavailable inside the library exception) is file-access-denied - exceeded limits) to expected errors and lets every other exception propagate. Phase 13 gives the image marks of a Vega-Lite chart the folder resolver of the viewer (the SvgImages wiring, based at the folder of the chart and under the same file-access policy, or the scoped resolver of an embedding document): a url draws a raster, an SVG file, a model, a page of a document, or another chart that the policy allows and never a remote resource, the drawn files are embed operations and the printed text of a model its echo, a link that was not drawn is the resolver's warning (the library's duplicate vl-mark-image-unresolved is dropped) and an unsupported-feature error in strict mode, a picture that is found but broken is the error of its own failure naming both files, more pictures than the limit is budget-exceeded, and the probe measures the chart without any picture. The unit includes BoxOptions (the options that load a source into a box: vector sources are rendered natively at the box), and the supporting model types SourceKind, OutputFormat, SourceInfo, SourceOptions, ScadViewOptions, ScadView, SourceDirective, ChartFacts, ChartDataReference, DiagramFacts, DiagramOptions, LoadedSource, AppliedOperation, ImageDiagnostic, and SourcePage. SourceOptions.VegaLite (ChartOptions: the values of the parameters of a chart and WarnOnUnknownParameters) sets the parameters of a Vega-Lite chart: it is validated before any file is touched, the chart is measured again with the values so the natural size and the page are those of the parameterized chart, the render operation lists them in a params field, and a name the chart does not declare is a vega-lite-error that lists the declared names (or the warning vl-param-unknown with WarnOnUnknownParameters). The fragment of an input path (part.scad#def.explode=0.5, report.pdf#page=3) is read by InputReference.Parse (a number sign starts a fragment only when no file has the name as written; the longest existing file before a number sign is the path) and Probe(InputReference), which reads the fragment with the built-in image source of the kind of the file, so an input and a link accept the same parameters and values (page, slide, view, def. variables including vectors such as $vpt, param. chart parameters, the theme of a diagram), refuses an unusable value with image-fragment-invalid and a missing page with page-out-of-range, reports an unknown or repeated parameter and an undeclared chart parameter as warnings (image-fragment-unknown-parameter, image-fragment-duplicate-parameter, vl-param-unknown) with the first page that is loaded, and returns the result as the InputSelection of the SourceInfo, which Load and OpenPages (and so every operation) lay over the options of the command with the fragment winning; the viewport variables $vpt, $vpr, $vpd, and $vpf set through -D or def. fix the camera so that several pictures of one model share a scale. */

        comment sourceRef /* Source: src/DemaConsulting.CanvasNet.Viewer/Imaging/SourceLoader.cs, src/DemaConsulting.CanvasNet.Viewer/Imaging/SourceLoader.Detect.cs, src/DemaConsulting.CanvasNet.Viewer/Imaging/SourceLoader.Raster.cs, src/DemaConsulting.CanvasNet.Viewer/Imaging/SourceLoader.Svg.cs, src/DemaConsulting.CanvasNet.Viewer/Imaging/SourceLoader.SvgImages.cs, src/DemaConsulting.CanvasNet.Viewer/Imaging/SourceLoader.Documents.cs, src/DemaConsulting.CanvasNet.Viewer/Imaging/SourceLoader.Pdf.cs, src/DemaConsulting.CanvasNet.Viewer/Imaging/SourceLoader.Pptx.cs, src/DemaConsulting.CanvasNet.Viewer/Imaging/SourceLoader.Vsdx.cs, src/DemaConsulting.CanvasNet.Viewer/Imaging/SourceLoader.Scad.cs, src/DemaConsulting.CanvasNet.Viewer/Imaging/SourceLoader.VegaLite.cs, src/DemaConsulting.CanvasNet.Viewer/Imaging/SourceLoader.Mermaid.cs, src/DemaConsulting.CanvasNet.Viewer/Imaging/SourceLoader.Input.cs, src/DemaConsulting.CanvasNet.Viewer/Imaging/InputReference.cs, src/DemaConsulting.CanvasNet.Viewer/Imaging/InputSelection.cs, src/DemaConsulting.CanvasNet.Viewer/Imaging/SourceModels.cs */
        comment testRef /* Test: test/DemaConsulting.CanvasNet.Viewer.Tests/Imaging/SourceLoaderTests.cs, test/DemaConsulting.CanvasNet.Viewer.Tests/Imaging/SourceLoaderVegaLiteImageTests.cs, test/DemaConsulting.CanvasNet.Viewer.Tests/Imaging/SourceLoaderVectorTests.cs, test/DemaConsulting.CanvasNet.Viewer.Tests/Imaging/SourceLoaderScadTests.cs, test/DemaConsulting.CanvasNet.Viewer.Tests/Imaging/SourceLoaderVegaLiteTests.cs, test/DemaConsulting.CanvasNet.Viewer.Tests/Imaging/SourceLoaderMermaidTests.cs, test/DemaConsulting.CanvasNet.Viewer.Tests/Imaging/SourceLoaderMermaidImageTests.cs, test/DemaConsulting.CanvasNet.Viewer.Tests/Imaging/SourceLoaderSvgImageTests.cs, test/DemaConsulting.CanvasNet.Viewer.Tests/Imaging/SourceLoaderDiagnosticDetailTests.cs, test/DemaConsulting.CanvasNet.Viewer.Tests/Imaging/SourceLoaderInputTests.cs, test/DemaConsulting.CanvasNet.Viewer.Tests/Imaging/SourceLoaderOptionsValidationTests.cs, test/DemaConsulting.CanvasNet.Viewer.Tests/Imaging/InputSelectionTests.cs */
        comment designRef /* Design: docs/design/canvas-net-viewer/imaging/source-loader.md */
        comment verificationRef /* Verification: docs/verification/canvas-net-viewer/imaging/source-loader.md */
        comment reqRef /* Requirements: docs/reqstream/canvas-net-viewer/imaging/source-loader.yaml */
    }
}
