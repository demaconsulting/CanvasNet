package CanvasNet {
    part def ExpressionFunctions {
        doc /* The internal static partial ExpressionFunctions with the ExpressionFunction delegate, the ExpressionFunctionContext, and the ExpressionRegex class: the closed table of the whitelisted pure functions that an expression may call (abs, acos, acosh, asin, asinh, atan, atan2, atanh, ceil, clamp, cos, cosh, exp, floor, log, log10, max, min, pow, round, sign, sin, sinh, sqrt, tan, tanh, trunc; lower, upper, trim, substring, slice, indexof, lastindexof, startswith, endswith, includes, replace, split, join, pad, length; isArray, isBoolean, isDate, isFinite, isNaN, isNumber, isObject, isRegExp, isString, isValid, toBoolean, toDate, toNumber, toString; regexp, test; the number format function format; and, from Phase 8, the date and time functions datetime, utc, time, timezoneoffset, date, day, year, month, hours, minutes, seconds, milliseconds, quarter, week, isoweek, dayofyear and their utc forms, timeOffset, utcOffset, timeSequence, utcSequence, timeUnitSpecifier, timeFormat, utcFormat, timeParse, utcParse, monthFormat, monthAbbrevFormat, dayFormat, and dayAbbrevFormat), 100 functions in all, with Names, TryGet, and Invoke (an unknown name is an ArgumentException) and no clock (now is not provided), no sampling function (random, sampleNormal, sampleLogNormal, and sampleUniform are not in the table: an expression is a pure deterministic function of its datum and parameters and Vega's random is the unseeded Math.random), reflection, file, or network function. The functions follow JavaScript and Vega results independently of the culture (negative zero kept, isNaN and isFinite not coercing, toBoolean, toNumber, and toString giving null for null and the empty string, pad aligned as in Vega), results are bounded by MaxStringLength, and the host math library is used for the transcendental functions. The date functions read and write dates through the TimeCalendar of the context (UTC when none is given; the utc functions always use UTC; years 0 to 99 are 1900 to 1999 and an instant outside the years 1 to 9999 is null or NaN), the format functions use TimeFormat (the string specifier compiled and cached per context, an object specifier a multi-format), a sequence is bounded by MaxScaleDomainSize and charged one step per date, and the specifier and text lengths of a format or a parse are charged. The format function (ExpressionFunctions.Number.cs) is Vega's d3-format number format on the NumberFormat unit of the Scales subsystem (en-US, the minus sign U+2212, culture-independent; a new namespace dependency of Expressions on Scales): a null value gives the text null, any other value is coerced like the JavaScript unary plus (an unreadable text or object is NaN) except for the type c, which prints the original value as JavaScript text (NumberFormat.IsText and FormatText), the specifier is read as text, an invalid specifier is a located VegaLiteRenderException (an ExpressionRuntimeException invalid format), and the specifier and the result are charged to the step budget and bounded by MaxStringLength. The ExpressionFunctionContext is the per-evaluation context that carries the calendar, counts the steps (Step, ChargeSteps, and ChargeSize for one step per 64 characters or elements of size-proportional work), polls the cancellation token, enforces the string limit, and caches at most 64 regular expressions, 64 time formatters, and 64 number formatters (GetNumberFormatter, for specifiers of at most 64 characters); ExpressionRegex translates a JavaScript pattern (the flags g, i, m, and s, with u, v, y, and d rejected; at most 1,024 characters; \d, \w, and $ semantics adjusted) into a .NET Regex that uses RegexOptions.NonBacktracking with the invariant culture (a 5 second backstop timeout) and falls back for the patterns that engine rejects (look-around, back-references) to the backtracking engine with a 100 millisecond timeout that fails closed, an invalid or over-long pattern being a located VegaLiteRenderException. Color, geographic, scale, and dataflow functions, and now, are deferred and are reported by the FeatureCatalog, as are the sampling functions random, sampleNormal, sampleLogNormal, and sampleUniform, which are not planned. */

        comment distributionRef /* Phase 14: the table also holds the nine probability distribution functions of Vega's statistical functions (ExpressionFunctions.Distributions.cs, a port of vega-statistics 2.0.0 normal.js, lognormal.js, and uniform.js) - densityNormal, cumulativeNormal, quantileNormal, densityLogNormal, cumulativeLogNormal, quantileLogNormal, densityUniform, cumulativeUniform, and quantileUniform - 113 functions in all. The cumulative normal is West's 2009 approximation shared with KernelDensity.NormalCdf and the normal quantile uses the inverse error function of Giles in the form of Apache Commons Math that Vega ports. The JavaScript defaults and coercions are reproduced (mean || 0, stdev == null ? 1 : stdev, a uniform without a maximum is the interval from 0 to the minimum, relational comparison semantics, the + concatenation when a text mean or minimum is given to a quantile) and a quantile outside 0 to 1 is NaN; every call is pure, deterministic, and a constant amount of work. */

        comment selectionRef /* Phase 12 (milestone 2): the table also holds the selection functions of Vega - data (the tuples of a selection store of the call, an empty array for any other name) and vlSelectionTest, vlSelectionIdTest, and vlSelectionResolve (SelectionTestSemantics, a port of vega-selections: an enumerated scalar by strict equality, a list by membership, a range with inclusive ends swapped when reversed, a bin that excludes its end, dates as milliseconds, tuples united by default and, for intersect, united within a unit and intersected across units, the number zero for a store without tuples; the resolution gives the selected values of each field and, for a point selection, the vlPoint query) - 104 functions in all with the selection functions (113 since Phase 14, see distributionRef); the stores (SelectionStore and SelectionEntry) are held by the per-evaluation ExpressionFunctionContext, and every field tested is charged one step. */
        comment sourceRef /* Source: src/DemaConsulting.CanvasNet.VegaLite/Expressions/ExpressionFunctions.Selection.cs, src/DemaConsulting.CanvasNet.VegaLite/Expressions/SelectionStore.cs, src/DemaConsulting.CanvasNet.VegaLite/Expressions/SelectionTestSemantics.cs, src/DemaConsulting.CanvasNet.VegaLite/Expressions/ExpressionFunctions.cs, src/DemaConsulting.CanvasNet.VegaLite/Expressions/ExpressionFunctions.Text.cs, src/DemaConsulting.CanvasNet.VegaLite/Expressions/ExpressionFunctions.Casing.cs, src/DemaConsulting.CanvasNet.VegaLite/Expressions/ExpressionFunctions.Types.cs, src/DemaConsulting.CanvasNet.VegaLite/Expressions/ExpressionFunctions.Regex.cs, src/DemaConsulting.CanvasNet.VegaLite/Expressions/ExpressionFunctions.Time.cs, src/DemaConsulting.CanvasNet.VegaLite/Expressions/ExpressionFunctions.Number.cs, src/DemaConsulting.CanvasNet.VegaLite/Expressions/ExpressionFunctions.Distributions.cs, src/DemaConsulting.CanvasNet.VegaLite/Expressions/ExpressionFunctionContext.cs, src/DemaConsulting.CanvasNet.VegaLite/Expressions/ExpressionRegex.cs */
        comment testRef /* Test: test/DemaConsulting.CanvasNet.VegaLite.Tests/Expressions/ExpressionFunctionsSelectionTests.cs, SelectionTestSemanticsTests.cs, ExpressionFunctionsTests.cs, ExpressionFunctionsTimeTests.cs, ExpressionFunctionsNumberTests.cs, and ExpressionFunctionsDistributionTests.cs */
        comment designRef /* Design: docs/design/canvas-net-vega-lite/expressions/expression-functions.md */
        comment verificationRef /* Verification: docs/verification/canvas-net-vega-lite/expressions/expression-functions.md */
        comment reqRef /* Requirements: docs/reqstream/canvas-net-vega-lite/expressions/expression-functions.yaml */
    }
}
