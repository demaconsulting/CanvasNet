package CanvasNet {
    part def ExpressionEvaluator {
        doc /* The internal ExpressionEvaluator (a sealed partial class created once per render call, for one thread) with the IExpressionDatum interface: Evaluate runs a CompiledExpression as an iterative loop over its postfix program with a reusable value stack, with no datum, with a DataTable row (the flattened nested fields rebuilt on demand as arrays and objects that keep their identity within the evaluation), with a DataValue object, or with a caller-defined IExpressionDatum. It follows JavaScript and Vega semantics independently of the culture - string concatenation, numeric coercion (null is 0, NaN, signed infinities, negative zero), strict and loose equality by the ECMAScript tables, relational ordering, operand-returning logical operators, short-circuit and conditional evaluation that neither runs nor charges the skipped operand, null-safe member and index access on objects, arrays, and strings, array and object literals (an object keeps the first position and the last value of a repeated key), composite equality by identity, dates as milliseconds with an ISO text form - and reads a parameter by ordinal name from the dictionary the caller built (an unknown name is null) and evaluates every unsupported construct to null. One MaxEvaluationSteps budget is shared by all evaluations of the evaluator (one step per instruction, one more per 64 characters or elements of function work; a program of N instructions passes with a limit of N and fails with N - 1), MaxStringLength bounds concatenation, and the cancellation token is checked at the start of every evaluation and whenever the step counter crosses a multiple of 1,024; strict equality of two texts charges steps by the shorter length (so a long filter comparison is bounded by the same budget); failures are VegaLiteRenderExceptions located at the expression string with the expression offset in the message, and cancellation is an OperationCanceledException. IsTruthy, ToNumber, ToJsString, StrictEquals, LooseEquals, and NumbersEqual are the coercion helpers shared with the transforms. Phase 8 gives the evaluator the time calendar of the chart (a constructor parameter, UTC when none is given) and passes it to the function context of every evaluation, so that the date functions of an expression read the time zone that the caller chose. */

        comment sourceRef /* Source: src/DemaConsulting.CanvasNet.VegaLite/Expressions/ExpressionEvaluator.cs, src/DemaConsulting.CanvasNet.VegaLite/Expressions/ExpressionEvaluator.Coercion.cs, src/DemaConsulting.CanvasNet.VegaLite/Expressions/ExpressionEvaluator.Datum.cs */
        comment testRef /* Test: test/DemaConsulting.CanvasNet.VegaLite.Tests/Expressions/ExpressionEvaluatorTests.cs, test/DemaConsulting.CanvasNet.VegaLite.Tests/Expressions/ExpressionTestSupport.cs */
        comment designRef /* Design: docs/design/canvas-net-vega-lite/expressions/expression-evaluator.md */
        comment verificationRef /* Verification: docs/verification/canvas-net-vega-lite/expressions/expression-evaluator.md */
        comment reqRef /* Requirements: docs/reqstream/canvas-net-vega-lite/expressions/expression-evaluator.yaml */
    }
}
