package CanvasNet {
    part def ExpressionParser {
        doc /* The internal ExpressionParser (a sealed partial class with the static Parse(source, location, limits) entry point) with the ExpressionToken and ExpressionTokenKind tokenizer types, and the CompiledExpression, ExpressionOpcode, ExpressionInstruction, ExpressionTables, ExpressionFindings, ExpressionConstruct, ExpressionConstructKind, ExpressionReference, and ExpressionRuntimeException types: a tokenizer and precedence-climbing parser with an explicit token cursor that compiles in a single pass to a postfix stack-machine program with forward jumps for the short-circuit and conditional operators (so neither compiling a left-associative chain nor evaluating a program recurses in proportion to the text; the nesting counter covers groups, brackets, call argument lists, array and object literals, conditional branches, and unary operands). It accepts null, booleans, finite decimal, hexadecimal, and exponent numbers, strings with escapes, regular expression literals with the flags g, i, m, and s (u, v, y, and d are rejected), array and object literals, the constants PI, E, NaN, and Infinity, datum, datum.x, datum['a b'], member and index access, the unary, arithmetic, relational, equality, logical, and conditional operators, grouping, and calls by name; assignment, method calls, new, function expressions, arrow functions, the comma, the semicolon, ** and ?? are syntax errors. MaxExpressionLength is checked before tokenizing for an expression that the user wrote (Parse), eight times MaxSourceLength for the expression that the renderer writes from a predicate or a composite mark (ParseGenerated; the writer of a predicate counts the characters as it writes and refuses a text over that budget before allocating it, with the same error, through GeneratedBudget and GeneratedTooLong), and MaxExpressionDepth while compiling; every problem is a VegaLiteSpecException at the location of the string value that holds the expression with the zero-based expression offset in the message. The immutable CompiledExpression carries the source, location, depth, instruction count, whether it reads the datum, the unsupported constructs in order (vl-expr-function-name with the name lower-cased and the construct keeping the name as written, vl-expr-view-state, vl-expr-construct-name), and the parameter references (one per name with the offset of its first use). */

        comment sourceRef /* Source: src/DemaConsulting.CanvasNet.VegaLite/Expressions/ExpressionParser.cs, src/DemaConsulting.CanvasNet.VegaLite/Expressions/ExpressionParser.Primary.cs, src/DemaConsulting.CanvasNet.VegaLite/Expressions/ExpressionParser.Tokenizer.cs, src/DemaConsulting.CanvasNet.VegaLite/Expressions/CompiledExpression.cs, src/DemaConsulting.CanvasNet.VegaLite/Expressions/ExpressionConstruct.cs, src/DemaConsulting.CanvasNet.VegaLite/Expressions/NamespaceDoc.cs */
        comment testRef /* Test: test/DemaConsulting.CanvasNet.VegaLite.Tests/Expressions/ExpressionParserTests.cs */
        comment designRef /* Design: docs/design/canvas-net-vega-lite/expressions/expression-parser.md */
        comment verificationRef /* Verification: docs/verification/canvas-net-vega-lite/expressions/expression-parser.md */
        comment reqRef /* Requirements: docs/reqstream/canvas-net-vega-lite/expressions/expression-parser.yaml */
    }
}
