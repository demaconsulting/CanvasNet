package CanvasNet {
    part def VegaLiteTransforms {
        doc /* The internal subsystem in the DemaConsulting.CanvasNet.VegaLite.Transforms namespace that turns the rows a chart loads into the rows it draws, after the DataLoader and before the scales: its RowTransforms unit runs the row transforms of the drawn view eagerly and in their written order, each reading an immutable DataTable and producing a new one - calculate (an expression per row, adding or replacing a field), filter (an expression or the predicates equal, lt, lte, gt, gte, range, oneOf, and valid composed with and, or, and not, and param for a static variable parameter), fold, flatten, sample (deterministic reservoir seeded from the transform's JSON pointer), pivot (every aggregate operation of Vega, computed by the aggregate cells of the AggregateTransforms unit), and lookup (a secondary source loaded through the same per-call DataLoader, first match wins) - and builds the static parameter environment (the value or expression of each variable parameter of the drawn view, evaluated once in dependency order and replaced by the caller's Parameters render option). The row budget of the call is the DataLoader's: fold and flatten reserve their output before allocating it, a dropped input is released, lookup sources are counted as any source, MaxFieldCount, MaxStringLength, a 2^25 cell bound, and the evaluation steps are enforced with located VegaLiteRenderExceptions, and cancellation is checked between transforms and at least every 1,024 rows. Recoverable problems are the warnings vl-expr-runtime and vl-transform-runtime. Phase 6 adds the grouping transforms and the implicit encoding pipeline: the AggregateTransforms unit runs aggregate (24 operations, structural group keys in first-seen order, a deterministic bootstrap for ci0 and ci1), joinaggregate, window (13 window operations and the aggregate operations over frames with peers), bin (the nice step algorithm of the public Vega bin), stack (zero, center, and normalize offsets), and impute (a constant or a mean, median, max, or min over a frame) under the same limits, and the EncodingPlan unit plans, from the encoding alone, the implicit bin, aggregate, and stack of the channels (bin and aggregate fields, the stack of bar and area marks, the default titles) and applies them to the transformed table, producing the raw and the main tables that the scales, marks, and axes read, under the same row, cell, string, bin-count, and step limits, with the groups of an aggregate reserved in the row budget as they appear. Phase 8 adds the time unit: the TimeUnitTransform unit adds the start and end fields of a time unit (the floor of the date in the time zone of the chart, or in UTC for a utc unit, and one step later, as date values, with null for a value that is not a date) for the timeUnit transform and for the implicit time unit step of an encoding, and collects the fields that the loader parses implicitly as dates; the EncodingPlan unit plans the time unit fields (names such as yearmonth_date, the _end field, the band end, and the titles) and runs them between the bin and the aggregate; the RowTransforms unit dispatches the timeUnit transform and evaluates the time predicates of filters through compiled expressions in the time zone of the chart. Phase 13 adds the StatTransforms unit, which computes the statistical transforms regression, loess, density, quantile, and extent with the numerics of the Vega operators they compile to (the regression models, the curve sampler, the locally weighted regression, and the kernel density), replacing the table with the generated rows (extent sets a parameter that the following transforms, bin.extent, and scale.domain read, reported as null at a static site by the warning vl-param-extent-static), and every transform of Vega-Lite is computed; since Phase 12 (milestone 2) the SelectionModel unit builds the initial state of the selection parameters (the stores that the selection functions of the expression engine read, and the resolved value of each selection parameter) before the parameters are evaluated, and the conditions and filters on a selection are evaluated; since Phase 11 the transforms of every view of a composition (layers, concatenated charts, the cells of a facet on the rows of the cell, and the copies of a repeat) are applied, and the EncodingTransforms facet partition (bounded by MaxViews and MaxDataRows before any table is allocated) builds the tables of the cells; there is no clock or random source. The subsystem is internal and uses the Expressions and Data subsystems and the compiled expressions of the SpecModel subsystem. As of this release, its units are RowTransforms, AggregateTransforms, EncodingPlan, TimeUnitTransform, StatTransforms, and SelectionModel. */

        comment testRef /* Test: test/DemaConsulting.CanvasNet.VegaLite.Tests/Transforms/ (the unit test classes RowTransformsTests, RowTransformsTimeTests, AggregateTransforms*Tests, EncodingPlanTests, EncodingPlanTimeTests, EncodingTransformsTimeTests, TimeUnitTransformTests, TemporalFieldsTests, StatTransforms*Tests, and SelectionModelTests) */
        comment designRef /* Design: docs/design/canvas-net-vega-lite/transforms.md */
        comment verificationRef /* Verification: docs/verification/canvas-net-vega-lite/transforms.md */
        comment reqRef /* Requirements: docs/reqstream/canvas-net-vega-lite/transforms.yaml */

        part rowTransforms : RowTransforms;
        part aggregateTransforms : AggregateTransforms;
        part encodingPlan : EncodingPlan;
        part timeUnitTransform : TimeUnitTransform;
        part statTransforms : StatTransforms;
        part selectionModel : SelectionModel;
    }
}
