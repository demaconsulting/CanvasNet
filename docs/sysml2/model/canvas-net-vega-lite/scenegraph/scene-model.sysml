package CanvasNet {
    part def VegaLiteSceneModel {
        doc /* The immutable scene types of CanvasNetVegaLite (the unit's source classes are named SceneModel; the part def carries the VegaLite prefix because SceneModel already names a CanvasNetRender3D subsystem): Scene (width, height, background as a CSS color, root group) with iterative enumeration in drawing order (Enumerate, Find, FindAll, OfType, CountItems, reporting the accumulated group translation and depth), the abstract SceneItem record (a stable role, Fill and Stroke as CSS color strings, StrokeWidth, multiplying opacities, dash pattern, cap, and join) and its subtypes SceneGroup (a coordinate system with width, height, corner radius, clip, stroke offset, and ordered children), SceneRect, SceneRule, ScenePath (a points path or, when Segments is set, a path of absolute ScenePathSegment moves, lines, cubic Beziers, and closes that replaces its points), SceneSymbol (size as the area of the bounding box), SceneText (lines, offsets, font, align, baseline, angle, limit, line height, ellipsis), SceneArc (a center, an inner and an outer radius, a start and an end angle in radians, a pad angle, and a corner radius), SceneTrail (runs of SceneTrailPoint position and size), and (Phase 13) SceneImage (a link, an anchor, an optional width and height, the aspect and smooth flags, the left or center or right and top or middle or bottom anchors, and the location of the mark; the picture itself is loaded by the painter, never held by the scene), SceneItem also carrying an optional StrokeMiterLimit, the value types ScenePoint, SceneClip, and SceneEntry, the immutable linear SceneGradient (a start and an end as fractions of the item's bounding box, defaults left to right, a vertical form from the bottom to the top for legends, and a bounded read-only list of SceneGradientStop color stops) that an item can carry in FillGradient in place of its solid fill, SceneBounds (the empty box as the identity of Union, Translate, and Rotate with exact quarter turns), and SceneBudget, which counts every item of the scene, groups included, before the builders create it (a limit of N allows exactly N items), forks for the repeated axis passes, and fails with a located VegaLiteRenderException beyond MaxSceneItems. Items are immutable and list-valued members are copied, so everything a chart draws can be asserted analytically without pixels. */

        comment sourceRef /* Source: src/DemaConsulting.CanvasNet.VegaLite/Scenegraph/SceneModel.cs, src/DemaConsulting.CanvasNet.VegaLite/Scenegraph/SceneBounds.cs, src/DemaConsulting.CanvasNet.VegaLite/Scenegraph/SceneBudget.cs, src/DemaConsulting.CanvasNet.VegaLite/Scenegraph/NamespaceDoc.cs */
        comment testRef /* Test: test/DemaConsulting.CanvasNet.VegaLite.Tests/Scenegraph/SceneModelTests.cs, test/DemaConsulting.CanvasNet.VegaLite.Tests/Scenegraph/ScenePainterImageTests.cs */
        comment designRef /* Design: docs/design/canvas-net-vega-lite/scenegraph/scene-model.md */
        comment verificationRef /* Verification: docs/verification/canvas-net-vega-lite/scenegraph/scene-model.md */
        comment reqRef /* Requirements: docs/reqstream/canvas-net-vega-lite/scenegraph/scene-model.yaml */
    }
}
