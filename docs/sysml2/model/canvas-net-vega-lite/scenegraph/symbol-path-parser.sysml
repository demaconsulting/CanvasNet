package CanvasNet {
    part def SymbolPathParser {
        doc /* The internal SymbolPathParser (a sealed class with static parse and cache entry points) of the Scenegraph subsystem: the custom symbol shape. TryParse(text) reads SVG path data the way vega-scenegraph's path/parse.js does (the command letters and their parameter counts, the number and flag patterns, text before the first command skipped, a text with no command that draws nothing, an extended parameter list that repeats the command with a move-to repeating as a line-to, a smooth quadratic curve as the first command and more than 4,096 commands as errors) and gives a reason for a text that does not parse. Render(size) draws the parsed path scaled by the symbol radius sqrt(size) / 2 on both axes with the canvas rules of path/render.js (a command without a current point starts the path at its own point, a command after a close starts at the start of the closed sub-path, an operation with a number that is not finite is skipped, the arcs of path/arc.js are cubic curves of at most a quarter turn, s and S reflect the persisted control point whatever the previous command, and a scaled t always sees t as the previous command so its curve is skipped by the canvas and still counted by the bounds) and returns the core Path with the bounds of bound/boundContext.js (the end points and the extrema of the curves). TryGet keeps at most 256 parsed paths by their text, failures included, and Render remembers the last size. The renderer deviates from Vega, which throws for a path that does not parse: the FeatureCatalog reports the warning vl-shape-path-invalid and the ScenePainter draws a circle. The unit is used by the ScenePainter (the symbol of a point mark), the ScaleResolver (which shapes are drawable), the LegendBuilder (the bounds of a symbol), and the FeatureCatalog; it depends on the Geometry types of the core CanvasNet system and SceneBounds. */

        comment sourceRef /* Source: src/DemaConsulting.CanvasNet.VegaLite/Scenegraph/SymbolPathParser.cs */
        comment testRef /* Test: test/DemaConsulting.CanvasNet.VegaLite.Tests/Scenegraph/SymbolPathParserTests.cs */
        comment designRef /* Design: docs/design/canvas-net-vega-lite/scenegraph/symbol-path-parser.md */
        comment verificationRef /* Verification: docs/verification/canvas-net-vega-lite/scenegraph/symbol-path-parser.md */
        comment reqRef /* Requirements: docs/reqstream/canvas-net-vega-lite/scenegraph/symbol-path-parser.yaml */
    }
}
