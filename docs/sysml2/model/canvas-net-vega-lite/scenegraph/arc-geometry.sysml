package CanvasNet {
    part def ArcGeometry {
        doc /* The internal ArcGeometry (a static class, with the internal ArcPathWriter helper in the same file) of the Scenegraph subsystem: the geometry of the arc mark. Build(innerRadius, outerRadius, startAngle, endAngle, padAngle, cornerRadius) is a literal port of the d3-shape arc generator that returns a closed core Path centered at the origin: the radii are swapped when they are in the wrong order, angles are in radians measured clockwise from twelve o'clock (Vega's convention, the point of an angle a being (r sin a, -r cos a)), a sector is the outer arc, the line to the inner radius, the inner arc back, and the close (a wedge to the center when the inner radius is not above zero), a span of a whole turn or more is a disc or an annulus made of two half arcs for each circle with the inner circle wound the opposite way so that the nonzero fill leaves a hole, the pad angle moves each edge inward by the angle that leaves a gap of constant width (the arcsine of the pad radius over the radius times the sine of half the pad angle), and the corner radius rounds the corners with the tangent circles of d3-shape (clamped to half the thickness of the ring and to what the angle allows, with the two corners of an edge merged when they meet). ArcPathWriter ports the d3-path commands the generator needs (moveTo, lineTo, arc as an SVG elliptical arc with the epsilon rules of d3-path, closePath) and is also used by the ScenePainter for the capsules of a trail. The unit is total: a non-finite parameter or one beyond one billion gives an empty path, an outer radius of zero gives a point, negative radii, pad angles, and corner radii count as zero, and no coordinate that is not finite is emitted. It has no state and no dependency other than the Geometry types of the core CanvasNet system. */

        comment sourceRef /* Source: src/DemaConsulting.CanvasNet.VegaLite/Scenegraph/ArcGeometry.cs */
        comment testRef /* Test: test/DemaConsulting.CanvasNet.VegaLite.Tests/Scenegraph/ArcGeometryTests.cs */
        comment designRef /* Design: docs/design/canvas-net-vega-lite/scenegraph/arc-geometry.md */
        comment verificationRef /* Verification: docs/verification/canvas-net-vega-lite/scenegraph/arc-geometry.md */
        comment reqRef /* Requirements: docs/reqstream/canvas-net-vega-lite/scenegraph/arc-geometry.yaml */
    }
}
