package CanvasNet {
    part def ScenePainter {
        doc /* The internal ScenePainter (a sealed, stateless class) and the ScenePlacement record struct (Uniform, which enlarges the scene by a factor at the origin, and Fit, which scales it uniformly by the largest factor that fits a target and centers it): Paint draws a Scene onto a new or given core Surface using only the public CanvasNet drawing API. The surface is first filled with the background, then the items are drawn in list order; every path is transformed by the placement and the enclosing group translations before it is filled (the core library has no scale), fills are anti-aliased and flattened at a tolerance of 0.02 pixel, strokes are built in the item's own units with PathStroker (width, dash, cap, join) so they scale with the chart, opacity is folded into the alpha, and a paint that is none, unparseable, or fully transparent draws nothing. An item with a SceneGradient is filled with the core LinearGradient (pad spread) instead of its solid fill: the start and end are fractions of the bounding box of the item's path mapped to pixels with the same transform, the fill opacity scales every stop, unusable stops are dropped, a gradient that cannot be used falls back to the solid fill and a fully transparent one draws nothing. A group paints its own background (a solid color or a gradient) and border (offset by half a pixel for a one-pixel stroke, as Vega does) and, with a clip, draws its children onto a transparent layer the size of the clip's pixel box that is composited back with the per-pixel coverage of the clip rectangle (exact on integer edges, anti-aliased on fractional edges). Symbols use Vega's shape geometry (an unknown shape is a circle) rotated about the center; text is filled only, at the scaled size, with the font and lines of the TextMeasurer, at Vega's baseline offsets, rotated about the position. A ScenePath with segments is drawn from its absolute moves, lines, cubic Beziers, and closes (nonzero fill, a command after a close continuing at the start of the closed subpath, nothing for a coordinate that is not finite); a SceneArc is the outline of the ArcGeometry unit translated to its center; a SceneTrail is the union of the capsules between consecutive points as Vega's trail draws them (the width following the size of each point, a run ending at a point with no usable size, a circle for coincident points, the cancellation token polled every 1,024 points (a translucent trail that is painted in several chunks is composited once through coverage layers, so that the joints of the chunks show no seam; only a translucent solid fill, and a drawn stroke that is translucent or follows a layered fill (to keep the order of fill and stroke), get a layer, an opaque fill being painted directly, and none is allocated unless the trail has a second chunk; the layers cover the box of the points that can be drawn grown by the radius and the stroke width of a layered stroke, a width that is never stroked neither grows the box nor gets a layer, and the layers of one trail are charged against a pixel budget (32 Mi pixels by default) before they are allocated, a trail over it being painted chunk by chunk without them), implemented in ScenePainter.Paths.cs); and every stroke takes the miter limit of its item (4 when it has none, clamped to 1 through 1,000). The result is byte-identical for the same scene, size, and placement; a canceled token throws OperationCanceledException and disposes the surface it created. Phase 13 (ScenePainter.Images.cs and SceneImageSource.cs) draws the SceneImage items of the image mark by the rules of Vega's image mark (the box from the given width and height, else the aspect of the picture, else its natural size; the anchors; the fit-inside rule for a box of another aspect; a box without area drawing nothing), loading each picture at paint time through the SceneImageSource of the painting, which asks the host's IImageResolver once for each link and device size, counts the questions against MaxImages (a located VegaLiteRenderException beyond it), reports a picture the resolver did not give as the warning vl-mark-image-unresolved, lets the resolver's exceptions propagate, and disposes every surface when the painting ends; the picture is filled into its box through a core TilePaint (anti-aliased edges, area-averaged reduction) with the opacity of the item, and a painter without a loader draws no picture. A symbol whose shape is not a symbol name is drawn from the SVG path data that the SymbolPathParser parses and scales by the symbol radius (ScenePainter.SymbolPath), or as a circle when the text does not parse, and ScenePainter.IsDrawableShape tells whether a shape is drawn as itself. */

        comment sourceRef /* Source: src/DemaConsulting.CanvasNet.VegaLite/Scenegraph/ScenePainter.cs, src/DemaConsulting.CanvasNet.VegaLite/Scenegraph/ScenePainter.Paths.cs, src/DemaConsulting.CanvasNet.VegaLite/Scenegraph/ScenePainter.Images.cs, src/DemaConsulting.CanvasNet.VegaLite/Scenegraph/ScenePainter.Budget.cs, src/DemaConsulting.CanvasNet.VegaLite/Scenegraph/SceneImageSource.cs */
        comment testRef /* Test: test/DemaConsulting.CanvasNet.VegaLite.Tests/Scenegraph/ScenePainterTests.cs, test/DemaConsulting.CanvasNet.VegaLite.Tests/Scenegraph/ScenePainterPathTests.cs, test/DemaConsulting.CanvasNet.VegaLite.Tests/Scenegraph/ScenePainterImageTests.cs, test/DemaConsulting.CanvasNet.VegaLite.Tests/Scenegraph/ScenePainterBudgetTests.cs */
        comment designRef /* Design: docs/design/canvas-net-vega-lite/scenegraph/scene-painter.md */
        comment verificationRef /* Verification: docs/verification/canvas-net-vega-lite/scenegraph/scene-painter.md */
        comment reqRef /* Requirements: docs/reqstream/canvas-net-vega-lite/scenegraph/scene-painter.yaml */
    }
}
