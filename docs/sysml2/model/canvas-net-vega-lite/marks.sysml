package CanvasNet {
    part def VegaLiteMarks {
        doc /* The internal subsystem in the DemaConsulting.CanvasNet.VegaLite.Marks namespace that turns data rows, resolved scales, and mark properties into scene items: its MarkBuilder unit draws the marks bar, rect, point, circle, square, rule, and tick with the Vega-Lite 6 geometry (bands, continuous thickness, measure axis from the value to zero, symbols at the band center or value, rules and ticks) and paint (filled by default for every mark but point and rule, reduced default opacity for point-like marks and ticks, the property precedence of the mark definition, style, mark configuration, and Vega styles), drops rows with invalid values on continuous channels (the filter behavior of Vega-Lite 6), charges the scene-item budget for the marks group and each item before it is created (a located VegaLiteRenderException beyond MaxSceneItems; a row that draws nothing costs nothing), polls cancellation every 1,024 rows, and clips to the data rectangle only for clip true. Phase 5 evaluates the row-bound expr references of the color, fill, stroke, opacity, strokeWidth, and size values of the drawn view per row against the transformed table. Phase 7 colors marks from continuous (ramp), classified (quantize, quantile, threshold), and categorical scales and draws the shape, strokeWidth, strokeDash, fillOpacity, strokeOpacity, angle, and discretized size channels. Phase 8 draws the bars and rects of a time unit over their whole unit on a time scale and places the other marks of a time unit at the point of their unit that the band position names. Phase 9 draws the line, area, and trail marks as paths (one for each group of rows that share the grouping fields, sorted by the pixel position or the order channel, interpolated through the CurveBuilder unit with the fifteen Vega-Lite curves, broken at invalid rows or connected in the filter mode, with the point and line overlays and with stacked areas whose layers meet), the text mark (formatted labels in lines, with polar offsets) and the arc mark (pie, donut, and radial slices from the theta and radius channels), and sorts the draw order of every mark by the order channel. The marks image and geoshape are reported by the FeatureCatalog and yield an empty marks group; the composite marks boxplot, errorbar, and errorband are expanded into the primitive marks by the SpecNormalizer before the builder sees them, and the builder builds one marks group for each layer of a layered view. The subsystem is internal; its entry point is called by VegaLiteDocument once for the final data rectangle. As of this release, its units are MarkBuilder and CurveBuilder. */

        comment testRef /* Test: test/DemaConsulting.CanvasNet.VegaLite.Tests/Marks/ (the unit test classes MarkBuilderTests, MarkBuilderChannelTests, MarkBuilderConditionTests, MarkBuilderTimeTests, MarkBuilderPathTests, MarkBuilderOrderTests, MarkBuilderOverlayTests, MarkBuilderTextTests, MarkBuilderArcTests, MarkBuilderPolarTextTests, CurveBuilderTests, CurveBuilderSplineTests, and CurveBuilderAreaTests) */
        comment designRef /* Design: docs/design/canvas-net-vega-lite/marks.md */
        comment verificationRef /* Verification: docs/verification/canvas-net-vega-lite/marks.md */
        comment reqRef /* Requirements: docs/reqstream/canvas-net-vega-lite/marks.yaml */

        part markBuilder : MarkBuilder;
        part curveBuilder : CurveBuilder;
    }
}
