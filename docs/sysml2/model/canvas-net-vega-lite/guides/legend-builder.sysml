package CanvasNet {
    part def LegendBuilder {
        doc /* The internal LegendPlan, LegendBuilder, GuideTitle (the merge of the written and derived titles of the layers of an axis or a legend), and their records, own C# implementations with attribution of the legend rules of Vega-Lite and Vega: LegendPlan decides which of the channels color, size, shape, fill, stroke, strokeDash, strokeWidth, and opacity have a legend (a field or datum with a scale, unless the legend or scale is null or config.legend.disable is set), the kind of each (a gradient for a continuous color scale, a discrete gradient for a quantize, quantile, or threshold color scale, symbols otherwise), its orient and direction, its title, and merges channels whose domains are the same (the first channel is the canonical scale); LegendBuilder builds one legend as a legend group with a legend-entry group and a legend-title text - symbol legends with an entry per value (a domain, d3 ticks, or the classes of a discretizing scale with range labels, limited by symbolLimit with a final entry that counts the rest), laid out by the grid layout of Vega with rows of 2 and columns of 10 pixels, and gradient legends with a bar filled by a linear gradient whose stops are the ends of the domain and the ticks for a count of 15 (Vega scaleGradient), tick labels outside the bar thinned by LabelOverlap, or one band per class - and measures the box it needs from the entries, the title, and the padding. The unit fails with a located VegaLiteRenderException naming the limit when the values, ticks, label text, or scene items exceed MaxScaleDomainSize, MaxTicks, MaxStringLength, or MaxSceneItems (every scene item is charged before it is created, every loop polls the cancellation token), and with a located VegaLiteSpecException for an invalid format. The gradient stops and labels of a log, pow, sqrt, or symlog scale are placed along the transformed domain, and a log legend labels only the log ticks that Vega labels. The symbol legend of a bin-ordinal scale (a binned color) has one entry per bin labeled with the range of the bin, and the channels of the same binned field share one legend. A condition that holds a field has a legend of its field, conditions that hold only values have none, and the symbols of another legend show the first condition value and the largest opacity. Text is measured with the bundled fonts only. Phase 8 (LegendBuilder.Time.cs) builds the legends of temporal fields: the gradient of a temporal color with its labels at the time ticks of the scale (the tick count as a number or an interval, the minimum step of the unit) and the ramp sampled there, the symbols of a size or opacity on a time scale at its time ticks, and the symbols of an ordinal time unit field over its date values, labeling a date with the legend format, else the default format of the time unit, else config.timeFormat, through the TimeLabels unit and in the calendar of the scale (the legend's expression context takes it from the resolved scale), with explicit legend values read as dates. The legend symbol of a line, a rule, and a trail (which Vega-Lite draws unfilled in its legend) is the stroke shape painted with the stroke color (the size legend of a trail scales the stroke width of its symbols and keeps the symbol size, as Vega-Lite binds a trail size to strokeWidth), and that of an area, an arc, and a text is a filled circle (LegendPlan.cs, LegendMarkFacts). Phase 10 plans the legends of a layered view with LegendPlan.Create over LegendLayer (the view, its scales, and a scope function): for each channel one member for each scope from the first layer that has a legend for it, the titles of the other layers' fields joined as a, b, the legend properties of all the layers merged as Vega-Lite's mergeLegendComponent does (a property one layer gives wins over silence, the first layer wins a disagreement, differing explicit types give symbols, different explicit orients give a legend for each layer), the members of different layers and scopes merged as members of one view are, and the symbol facts from the first member's layer; a single layer plans exactly what the view overload plans. Phase 11 gives a LegendLayer the optional view node it comes from: LegendLayer.OwnerOf(channel) is the highest view above it whose resolve shares the legend of the channel (the children of a concatenation share the legends of color, size, shape, and the other non-position channels, and a legend that a view makes independent stays with the view below), LegendSpec.Owner is the owner of a planned legend, LegendPlan.Owners lists the owners in channel and layer order, and LegendPlan.Create with an owner plans the legends of that owner only (a view whose channels have different owners is planned once for each), never merging the layers of different owners; layers without nodes plan as before. The explicit labelExpr of a legend (the configuration has none in Vega-Lite 6.5) is applied by the LabelExpressions unit (the optional RowExpressions argument of the constructor shares the evaluator, the limits, and the parameters of the call) to the labels of the symbol legend (the ellipsis entry included), of the gradient legend (with datum.perc), and of the discrete gradient legend (with datum.perc and datum.perc2) before the entries are measured, so that the replaced text decides the width of the legend. Phase 12 (LegendDimming.cs) draws the legend that a selection is bound to (bind legend, a global selection that projects one field) in the initial state of the selection: LegendPlan.Create takes the optional SelectionModel, finds the selections of the unit view of the first layer that project the field or the channel of the first member, and LegendSpec.Dimming holds what each holds for the field; the symbols of a symbol legend that does not explain opacity (with the opacity of the symbol, or 1 when the legend has a symbolOpacity) and the labels of every legend (with 1) get config.legend.unselectedOpacity (0.35) for each entry whose value the selection does not hold by strict equality, and nothing is dimmed while the store of the selection is empty. Phase 13 draws every legend titleOrient (top, bottom, left, and right) as a port of legendGroupLayout, legendTitleOffset, and legend-title.js: the entries move right by the width of a left title and down by the height of a top title, a right title goes past the entries and a bottom title below them, the title anchor defaults to middle for left and right, the title of a vertical gradient is turned at the sides, and titleAlign and titleBaseline win; and a clipHeight greater than 0 on a symbol legend (Phase 14: a port of legend-symbol-groups.js, group.js, boundClip.js, and legendEntryLayout) puts the symbol and the label of each entry at half of clipHeight instead of half of the entry size, gives the entry group the label bounds united with the rectangle (0, 0) to (0, clipHeight), and wraps each symbol in a clipping group (scene role legend-symbol-clip) as wide as the widest entry of its column and as high as the bottom edge of the entry, so that vl-guide-legend-clipheight is retired (a gradient legend ignores clipHeight, as Vega does); a symbolType that is SVG path data is measured with the bounds of its drawing (SymbolPathParser). */

        comment sourceRef /* Source: src/DemaConsulting.CanvasNet.VegaLite/Guides/LegendPlan.cs, LegendBuilder.cs, LegendBuilder.Symbols.cs, LegendBuilder.Gradient.cs, LegendBuilder.Grid.cs, LegendBuilder.Time.cs, and LegendDimming.cs */
        comment testRef /* Test: test/DemaConsulting.CanvasNet.VegaLite.Tests/Guides/LegendPlanTests.cs, LegendPlanLayerTests.cs, LegendPlanCompositionTests.cs, LegendBuilderTests.cs, LegendPlanConditionTests.cs, LegendBuilderTimeTests.cs, LegendBuilderPathMarkTests.cs, LegendBuilderLabelExprTests.cs, LegendBuilderSelectionTests.cs, LegendBuilderTitleOrientTests.cs, and LegendBuilderClipHeightTests.cs */
        comment designRef /* Design: docs/design/canvas-net-vega-lite/guides/legend-builder.md */
        comment verificationRef /* Verification: docs/verification/canvas-net-vega-lite/guides/legend-builder.md */
        comment reqRef /* Requirements: docs/reqstream/canvas-net-vega-lite/guides/legend-builder.yaml */
    }
}
