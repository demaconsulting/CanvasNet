package CanvasNet {
    part def AxisBuilder {
        doc /* The internal AxisBuilder (a sealed class) with the AxisRequest, AxisTick, and AxisResult records: Build creates the axis of a linear, band, or point position scale as an axis scene group (ticks, labels, domain line, and title, with Vega's half-pixel translate, tick and grid position rounding, band offset, extent clamping between minExtent and maxExtent, and title placement) plus a separate grid group that is drawn behind everything, together with the bounds the axis needs; null when the axis is switched off. Every scene item (the axis group, the grid group, each grid line, tick, remaining label, the domain line, and the title) is charged to the scene budget before it is created. Properties are looked up in the axis, then the Vega-Lite-only configuration, then the Vega configuration (axisBand, the orient variants, axisX and axisY, axis, the Vega defaults), then the guide styles, with the Vega-Lite rules for the default grid, the label angle of a discrete x axis, label flush, label overlap, and z-index. Continuous ticks use the Ticks and NumberFormat units with Vega-Lite's tick count (one per 40 pixels, one per 10 pixels for a binned scale), the title lines come from the scale (the default titles of aggregates and bins, such as Sum of x, Count of Records, and x (binned)) unless the axis or the channel sets one, a normalized stack uses the configured normalizedNumberFormat as its default format, the grid is off for a binned field, explicit values follow Vega's validTicks, and band and point scales label every category; Vega's parity and greedy label overlap removal is applied. The static GetExtents unites the axes' bounds with the data rectangle for the ViewLayout. An invalid axis orient or d3 format is a VegaLiteSpecException with the location, an axis beyond MaxTicks is a VegaLiteRenderException with the location of the channel, and cancellation is polled per tick. A log axis has ten ticks by default (the log ticks), labels only the ticks that d3's log rule keeps with the variable-precision format (explicit values are all labeled), and thins overlapping labels greedily by default; pow, sqrt, and symlog axes use the ordinary ticks at the transformed positions. Axis legends, encode overrides, and custom format types are reported by the FeatureCatalog and not drawn. Phase 8 builds the axis of a time or UTC scale (and of an ordinal or nominal field with a time unit): the ticks are the d3 time ticks of the scale in its calendar (the tick count as a number, an interval name, or an interval and a step; the default count of the axis length divided by 40, but Vega's ten for a field whose time unit is exactly a month, hours, a day, or a quarter; the duration of one step of the unit as the minimum tick step; explicit values as timestamps, date texts, or datetime objects), the labels come from the TimeLabels unit (a d3 time format, a multi-format with overrides, the default format of the time unit, or the default multi-format, which ignores config.timeFormat; the format type number formats the millisecond value and the format types time and utc force time labels), and the defaults are a grid, label flush for a temporal x axis, the parity overlap method for a temporal field and for a time unit field without a sort object, and no label rotation for a time unit field (axisTemporal and axisXTemporal configuration apply); ticks beyond MaxTicks and labels beyond MaxStringLength are located VegaLiteRenderExceptions. Phase 10 adds the optional DefaultOrient and DefaultGrid of the AxisRequest: the side and the grid that a layered view gives the second independent axis of a channel (the opposite side, no grid) when the axis object names none, overridden by an explicit orient or grid and unchanged for a request that names no default. Phase 11 adds the optional InHeader of the AxisRequest for the axis that the cells of a facet share (Vega-Lite's mergeChildAxis): the axis group is placed at the origin of the header or footer that holds it (the bottom and right axes at their offset from it instead of at the far edge of the data rectangle), AxisResult.Bounds are in the coordinates of that header, the grid group stays where the cell draws it, and a request without InHeader builds as before. The labelExpr of the axis (or else of config.axis, axisX or axisY, axisBand, and the other axis configuration, in the precedence of the other axis properties) is applied by the LabelExpressions unit after BuildTicks (the optional RowExpressions argument of the constructor shares the evaluator, the limits, and the parameters of the call): AxisTick.Lines holds the replaced text, so that the label limit, the overlap removal, the measured extent, and the drawn labels all see it (an array result is a multi-line label), and an axis whose labels are off never evaluates the expression. Phase 13 draws the static axis properties: tickBand (extent is the end of the band with an extra tick and no offset, any other value the middle without an extra tick, and otherwise the band is bandPosition with tickExtra), the extra tick appended after the label expression at the start of the first band (the labels skip it), bandPosition for the ticks and the grid but not the labels (Phase 14: the position that holds a ranged offset, Vega-Lite's defaultBandPosition and labelsPositionSpec, defaults its bandPosition to 0 for x and 1 for y and puts the labels at the band position of the axis, an explicit bandPosition winning and 0.5 leaving them in the middle), translate (0.5 by default, replacing the half pixel of the origin of the axis group, not the bin shift of a bar), position (the axis moved along itself), titleX and titleY (the title position in the pixels of the axis group), and labelBound (true is a tolerance of 1 pixel, a number the tolerance, 0 and false none; it applies only when a label overlap method is set, as the Overlap transform of Vega returns before the test otherwise, and skips boxes of at most 1 pixel). */

        comment sourceRef /* Source: src/DemaConsulting.CanvasNet.VegaLite/Guides/AxisBuilder.cs */
        comment testRef /* Test: test/DemaConsulting.CanvasNet.VegaLite.Tests/Guides/AxisBuilderTests.cs, AxisBuilderTimeTests.cs, AxisBuilderHeaderTests.cs, AxisBuilderLabelExprTests.cs, AxisBuilderStaticPropertiesTests.cs, and AxisBuilderRangedOffsetTests.cs */
        comment designRef /* Design: docs/design/canvas-net-vega-lite/guides/axis-builder.md */
        comment verificationRef /* Verification: docs/verification/canvas-net-vega-lite/guides/axis-builder.md */
        comment reqRef /* Requirements: docs/reqstream/canvas-net-vega-lite/guides/axis-builder.yaml */
    }
}
