package CanvasNet {
    part def LabelExpressions {
        doc /* The internal LabelExpressions unit (LabelExpressions.cs, with the LabelText record struct) of the Guides subsystem: the evaluation of the labelExpr of axes, legends, and facet headers with the semantics of Vega-Lite 6.5 and Vega 6.4, run on the expression engine and the shared evaluator of the call (the same MaxEvaluationSteps, MaxStringLength, cancellation, and parameter values as every other expression) before the labels are measured, laid out, and thinned for overlap. Datum builds the datum object of Vega (value and label for every guide; for an axis index, the position of the tick as a fraction i / (n - 1), or zero for a single tick, and tickIndex, the integer position; for a symbol legend index, label, and value; for a gradient legend also perc, and for a discrete gradient also perc2; a facet header has value and label only), Resolve gets the compiled expression of a guide (the expression that the SpecParser compiled for the node, or the configured text compiled once and cached per instance, an invalid configured text being a located VegaLiteSpecException), and Evaluate runs it and turns the result into the text of the text mark of Vega (null is the empty text, an array gives lines whose elements are trimmed and whose null elements are empty, any other value is converted with the JavaScript string conversion and trimmed; a date is ISO text in this engine). The expression functions it evaluates include the number format function format and the time format functions. A limit that is exceeded is a located VegaLiteRenderException. The unit is used by AxisBuilder (also for the axis and header configuration), LegendBuilder (the explicit legend labelExpr only, because Vega-Lite 6.5 has no legend labelExpr in the configuration), and the header composition of the VegaLiteDocument unit, is culture-invariant, and belongs to one call and one thread. */

        comment sourceRef /* Source: src/DemaConsulting.CanvasNet.VegaLite/Guides/LabelExpressions.cs */
        comment testRef /* Test: test/DemaConsulting.CanvasNet.VegaLite.Tests/Guides/LabelExpressionsTests.cs */
        comment designRef /* Design: docs/design/canvas-net-vega-lite/guides/label-expressions.md */
        comment verificationRef /* Verification: docs/verification/canvas-net-vega-lite/guides/label-expressions.md */
        comment reqRef /* Requirements: docs/reqstream/canvas-net-vega-lite/guides/label-expressions.yaml */
    }
}
