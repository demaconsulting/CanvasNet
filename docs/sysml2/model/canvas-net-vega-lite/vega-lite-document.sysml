package CanvasNet {
    part def VegaLiteDocument {
        doc /* The public API of CanvasNetVegaLite in the DemaConsulting.CanvasNet.VegaLite namespace: the sealed, immutable, thread-safe VegaLiteDocument with the static Parse(string), Open(string path), and Open(Stream) entry points (strict UTF-8 with an optional byte-order mark, malformed UTF-8 rejected with a located VegaLiteSpecException, source limited to 4,194,304 characters by default, the stream left open and a non-terminating stream bounded), the SourceName, SchemaUrl, SchemaMajorVersion, Title, MarkTypes, DataReferences, and ParameterNames properties that describe the chart from its text alone, the Measure method that computes the size a chart renders at, and the two Render methods that draw the chart onto a new Surface (natural size times the scale, or an exact size with the chart scaled uniformly to fit and centered; invalid size or scale rejected before any report is delivered; warnings and unsupported-feature reports delivered once, in document order, on the calling thread; cancellation honored; byte-identical images from repeated and concurrent calls). The unit includes the immutable, validated VegaLiteOpenOptions (BaseDirectory, DataPaths, FileResolver, SourceName, Limits), VegaLiteRenderOptions (Scale, Background, Config, Parameters, Datasets, TimeZone, ContainerWidth, ContainerHeight, Fonts, Limits, the warning and unsupported-feature handlers, ThrowOnUnsupportedFeature), and VegaLiteFontOptions (UseSystemFonts, AdditionalDirectories); the VegaLiteLimits resource limits; the VegaLiteLocation record struct (file, JSON pointer, one-based line and column); the VegaLiteSpecException (a FormatException carrying the Location of the first problem), the VegaLiteRenderException (an InvalidOperationException carrying the Location of a failed render), and the VegaLiteUnsupportedFeatureException (an IOException carrying the feature and location); the VegaLiteDiagnostic and VegaLiteUnsupportedFeature records; the VegaLiteSize, VegaLiteDataReference, and VegaLiteDataKind types; and the internal VegaLiteReportSink that buffers, de-duplicates, caps, and delivers the reports. It delegates parsing to the internal VegaLiteSpecModel subsystem and the pipeline of data, scales, guides, layout, marks, and painting to the other internal subsystems, and opens no file and uses no network while parsing; only Measure and Render read data, creating one DataLoader per call from the effective open options (the folder of an opened file, BaseDirectory, DataPaths, or the FileResolver callback), the caller's Datasets, and the limits, loading the data before the scene budget is charged, and delivering the data warnings after the reports of the specification; a local data file that cannot be used is a VegaLiteRenderException and a remote URL is reported and never fetched. Phase 5 compiles the expressions and validates the parameters and transforms when the document is opened (a VegaLiteSpecException located at the offending value, with the expression offset in the message for an expression), and each measure or render call builds the static parameter environment (the specification's variable parameters replaced by the Parameters render option), runs the row transforms on the loaded table with the call's loader, limits, and cancellation token and one evaluator whose evaluation-step budget is shared by the parameters, the transforms, and the row-bound mark values, passes the transformed table to the scales and marks, and delivers the loader, lookup-source, and transform warnings in that order after the reports of the specification, also when a later stage fails. Phase 8 creates one time calendar per call from the TimeZone render option (UTC when it is not set; no host time zone, clock, or culture is ever used) and gives it to the DataLoader, the ExpressionEvaluator, and, through the resolved scales and the encoding data, to the transforms, scales, guides, and marks, and computes the set of the fields that are implicitly parsed as dates; the public API is unchanged. Phase 10 (VegaLiteDocument.Layers.cs) draws the layers of a layered view: the layer tree comes from SpecNormalizer.Expand (the composite marks boxplot, errorbar, and errorband replaced by their layers, MaxViews and MaxCompositionDepth enforced before any data is read), the data stage walks the tree depth first (the table of a view is that of the nearest data above it, the transform of each view runs before the views below read the table so a top-level transform is applied once, and each layer plans and runs its own implicit pipeline), the scales are resolved over all the layers with ScaleResolver.ResolveLayers and the step hints come from the merged discrete scale, the axes are planned for each position channel (one axis for the layers that share a scale and an axis with the titles joined, otherwise one for each group with the second on the opposite side and only the first with a grid, as Vega-Lite's parseLayerAxes does), the legends are planned over all the layers with their scopes, one group of marks is built for each layer in layer order, and the scale-conflict warnings follow the data warnings; a view without layer is one layer and takes exactly the steps it always took; the public API is unchanged. Phase 11 (VegaLiteDocument.Composition.cs) extracts the cell, the guides and the marks of one unit or layered view built for a data rectangle of a given size independently of the view that holds it (CreateCell, BuildCellGuides, BuildCell, BuildAxes, and BuildLegends, which places legends against any bounds), loads a table once for each data object of the specification with the date fields of every view that reads it (LayerTree.DataSites), and records for each planned axis the layers that share it and the view that owns it and for each legend the view that owns it, so that a composition can build its cells on its own; the scene of a single or layered view is unchanged and is pinned by snapshots. Phase 11 also draws the concatenations (concat, hconcat, vconcat) and the repeats that normalize to them: the Composer builds each chart of the tree as a cell of the size it resolves for itself (ViewLayout.ResolveSize with the step hints of its own scales, LayeredScales.HintsFor), with its own axes, marks, legends, and title, places the cells of each concatenation with CompositionLayout (columns, spacing, align, center, bounds), adds the legends that the charts of a concatenation share beside its grid (LegendPlan.Owners) and its title anchored at the start, and the canvas is the bounds of the content plus the padding (ViewLayout.Resolve with composition); the warnings of the view tree (vl-concat-axis-shared, vl-composition-columns-ignored, vl-repeat-ref-unresolved) are delivered once from the one tree that is drawn; a facet is drawn from the cells that the data stage makes for it: its cells are laid out with CompositionLayout together with the row and column headers (the labels of the values and the axes that the cells share, taken from the first cell of each row and column), the footers and the titles of its fields, the labels of a wrapped facet are the titles of its cells, and the legends that its cells share are its own, beside its grid. A single or layered view with autosize fit, fit-x, or fit-y, or a container width or height, is drawn into the size that is given by the same iteration of the guides with the layout (the legends counting only across their side), and a fit that a step size drops is the warning vl-layout-fit-step. The labelExpr of a facet header (of the header, then the row or column header configuration, then config.header) replaces the text of the labels and titles of the header blocks through a wrapper of the composition (WithLabelExpression) that evaluates it with the datum of a header (value and label only) on the evaluator of the call; an array result keeps its lines (the label function of the facet channel returns the lines, a string result with a line feed staying one line), which the header blocks and the layout measure. The unit also covers VegaLiteImageSource (the IImageSource for .vl and .vl.json files: laid out at the placement size on its own background, data files resolved in the folder of the request) for the shared image resolver of the core ImageSources subsystem. Phase 12 (milestone 1) changes the order of a call to parameters (evaluated first, with the caller's Parameters, whose values can now be arrays and string-keyed dictionaries of values nested up to 32 levels and holding at most 65,536 values, deep-copied when set), then the fold of the expression references of the static sites (ExpressionReferenceFolder), then the configuration, the normalization, the data, the transforms, the scales (which read the parameter values for a raw domain), and the marks. Phase 13 adds the optional ImageResolver of the render options (null by default; the only way the image mark gets a picture, since the library never opens a file or a network resource for it and Measure never asks it, asked from Render while the scene is painted through the SceneImageSource, with the link as written in the device size of the box) and the MaxImages limit (256 by default) of the distinct questions of one render; Run passes the report sink to the painting so that a picture the resolver did not give is the warning vl-mark-image-unresolved, ReportsFor visits the catalog again when a resolver or a configuration is given so that the image mark is reported as vl-mark-image only without a resolver, and VegaLiteImageSource passes the resolver of its request. The VegaLiteImageSource declares the fragment prefix param. (IFragmentImageSource): every param.name=value of a link sets a parameter of the chart through VegaLiteRenderOptions.Parameters like --param of the tool (a name the chart does not declare is the warning vl-param-unknown, an unusable value refuses the link with image-fragment-invalid). */

        comment selectionRef /* Phase 12 (milestone 2): PrepareChart builds the SelectionModel first (from the specification as written, only when it declares a selection), gives its stores to the expression evaluator and the resolved selections to the parameter environment, and delivers its warnings with those of the layer tree; the Parameters render option replaces the initial value of a selection (a map, a list of maps, a scalar, DateTime values; null clears it). */
        comment sourceRef /* Source: src/DemaConsulting.CanvasNet.VegaLite/VegaLiteImageSource.cs, src/DemaConsulting.CanvasNet.VegaLite/VegaLiteDocument.cs, src/DemaConsulting.CanvasNet.VegaLite/VegaLiteDocument.Render.cs, src/DemaConsulting.CanvasNet.VegaLite/VegaLiteDocument.Layers.cs, src/DemaConsulting.CanvasNet.VegaLite/VegaLiteDocument.Composition.cs, src/DemaConsulting.CanvasNet.VegaLite/VegaLiteOpenOptions.cs, src/DemaConsulting.CanvasNet.VegaLite/VegaLiteRenderOptions.cs, src/DemaConsulting.CanvasNet.VegaLite/VegaLiteFontOptions.cs, src/DemaConsulting.CanvasNet.VegaLite/VegaLiteLimits.cs, src/DemaConsulting.CanvasNet.VegaLite/VegaLiteLocation.cs, src/DemaConsulting.CanvasNet.VegaLite/VegaLiteSize.cs, src/DemaConsulting.CanvasNet.VegaLite/VegaLiteDataReference.cs, src/DemaConsulting.CanvasNet.VegaLite/VegaLiteDataKind.cs, src/DemaConsulting.CanvasNet.VegaLite/VegaLiteDiagnostic.cs, src/DemaConsulting.CanvasNet.VegaLite/VegaLiteUnsupportedFeature.cs, src/DemaConsulting.CanvasNet.VegaLite/VegaLiteSpecException.cs, src/DemaConsulting.CanvasNet.VegaLite/VegaLiteRenderException.cs, src/DemaConsulting.CanvasNet.VegaLite/VegaLiteUnsupportedFeatureException.cs, src/DemaConsulting.CanvasNet.VegaLite/VegaLiteReportSink.cs, src/DemaConsulting.CanvasNet.VegaLite/NamespaceDoc.cs */
        comment testRef /* Test: test/DemaConsulting.CanvasNet.VegaLite.Tests/VegaLiteSelectionIntegrationTests.cs, test/DemaConsulting.CanvasNet.VegaLite.Tests/VegaLiteImageSourceTests.cs, test/DemaConsulting.CanvasNet.VegaLite.Tests/VegaLiteImageSourceParameterTests.cs, test/DemaConsulting.CanvasNet.VegaLite.Tests/VegaLiteImageMarkIntegrationTests.cs, test/DemaConsulting.CanvasNet.VegaLite.Tests/VegaLiteSystemIntegrationTests.cs, test/DemaConsulting.CanvasNet.VegaLite.Tests/VegaLiteChartIntegrationTests.cs, test/DemaConsulting.CanvasNet.VegaLite.Tests/VegaLiteLayerIntegrationTests.cs, test/DemaConsulting.CanvasNet.VegaLite.Tests/VegaLiteCompositeMarkIntegrationTests.cs, test/DemaConsulting.CanvasNet.VegaLite.Tests/VegaLiteConcatIntegrationTests.cs, test/DemaConsulting.CanvasNet.VegaLite.Tests/VegaLiteRepeatIntegrationTests.cs, test/DemaConsulting.CanvasNet.VegaLite.Tests/VegaLiteLabelExprIntegrationTests.cs, test/DemaConsulting.CanvasNet.VegaLite.Tests/VegaLiteOffsetIntegrationTests.cs, test/DemaConsulting.CanvasNet.VegaLite.Tests/VegaLiteDocumentLayoutTests.cs, test/DemaConsulting.CanvasNet.VegaLite.Tests/VegaLiteRefactorSnapshotTests.cs, test/DemaConsulting.CanvasNet.VegaLite.Tests/SpecModel/VegaLiteDocumentSpecModelTests.cs, test/DemaConsulting.CanvasNet.VegaLite.Tests/VegaLiteOpenOptionsTests.cs, test/DemaConsulting.CanvasNet.VegaLite.Tests/VegaLiteRenderOptionsTests.cs, test/DemaConsulting.CanvasNet.VegaLite.Tests/VegaLiteLimitsTests.cs, test/DemaConsulting.CanvasNet.VegaLite.Tests/VegaLiteLocationTests.cs, test/DemaConsulting.CanvasNet.VegaLite.Tests/VegaLiteRecordsAndExceptionsTests.cs, test/DemaConsulting.CanvasNet.VegaLite.Tests/VegaLiteReportSinkTests.cs, test/DemaConsulting.CanvasNet.VegaLite.Tests/Fixtures/ */
        comment designRef /* Design: docs/design/canvas-net-vega-lite/vega-lite-document.md */
        comment verificationRef /* Verification: docs/verification/canvas-net-vega-lite/vega-lite-document.md */
        comment reqRef /* Requirements: docs/reqstream/canvas-net-vega-lite/vega-lite-document.yaml */
    }
}
