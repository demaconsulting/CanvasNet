package CanvasNet {
    part def SelectionModel {
        doc /* The internal SelectionModel (a sealed partial class with the static Declares, Create, and Find, the stores, the resolved values, and the warnings), the SelectionComponent class, and the SelectionBind enumeration: the initial state of the selections of a specification, which a static chart paints the way vega-embed paints it first, with no event fired. Declares tells from the view objects whether a selection is declared (a parameter with select, or the legacy selection property), so a specification without one builds no model. Create declares each selection for the unit views it applies to (SelectionDeclarations.Assign: a selection of a unit view for that unit, a top-level selection of a composition for every unit or for those that its views name; a selection that two or more layers of a layered view receive is a duplicate that Vega rejects and is dropped, applied as an empty selection), reads the initial value (the value of the caller replacing the value of the specification, a null clearing it, a date-time object read in the calendar of the call and stored as milliseconds), projects the selection as Vega-Lite's project.ts does (an explicit fields and encodings, else the keys of the value, else the configured defaults - x and y for an interval, the row identity for a point; a channel without a field or with an aggregate skipped with the warning vl-param-selection-projection; a time unit over its derived field; tuple type R for an interval over a continuous scale, R-RE for a bin, otherwise E), maps each value to a tuple, builds the store of the first declaration of each name (SelectionEntry records in a SelectionStore; none for a dropped selection or a projection over row identities, which is not modeled and warns with vl-param-selection-id when the caller gave a value), and resolves each selection with SelectionTestSemantics.Resolve to the value of its signal (an object with the selected values of each field and, for a point selection, vlPoint). The stores go to the expression evaluator (data and the selection functions read them) and the resolved values to ParameterEnvironment, so that parameters, expression references, conditions, and filters see one state; bind, on, clear, toggle, nearest, translate, and zoom are ignored without a report,         and the bind kind and the resolve are kept for later stages. Phase 12 (milestone 2b) adds the queries that the later stages ask (SelectionModel.Queries.cs: BindUnits binds the model to the units of the drawn tree, a facet cell finding its template; ComponentsOf, FindComponent walking up the views, BoundExtentOf for a selection bound to the scales, and ResolveExtent for the selected range of a field that a scale domain or a bin extent names), the brush mark and the scale-bound flag of each component (the mark merged over config.selection.interval.mark; a scale-bound selection of a view that is not the whole view holds nothing), and the time units of the projected fields (SelectionTimeUnits.cs: the derived start and end fields that a filter or a condition of another view needs). Creating the model reads no data. */

                comment sourceRef /* Source: src/DemaConsulting.CanvasNet.VegaLite/Transforms/SelectionModel.cs, src/DemaConsulting.CanvasNet.VegaLite/Transforms/SelectionModel.Projection.cs, src/DemaConsulting.CanvasNet.VegaLite/Transforms/SelectionModel.Queries.cs, src/DemaConsulting.CanvasNet.VegaLite/Transforms/SelectionTimeUnits.cs */
                comment testRef /* Test: test/DemaConsulting.CanvasNet.VegaLite.Tests/Transforms/SelectionModelTests.cs, test/DemaConsulting.CanvasNet.VegaLite.Tests/Transforms/SelectionModelQueryTests.cs */
        comment designRef /* Design: docs/design/canvas-net-vega-lite/transforms/selection-model.md */
        comment verificationRef /* Verification: docs/verification/canvas-net-vega-lite/transforms/selection-model.md */
        comment reqRef /* Requirements: docs/reqstream/canvas-net-vega-lite/transforms/selection-model.yaml */
    }
}
