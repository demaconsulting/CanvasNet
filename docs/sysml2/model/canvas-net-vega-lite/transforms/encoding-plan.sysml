package CanvasNet {
    part def EncodingPlan {
        doc /* The internal EncodingPlan (a sealed class created from a view and its ResolvedConfig by the static Create) with the ChannelPlan, BinPlan, aggregate, and stack plan records, the BinKind enumeration, and the EncodingTransforms class with the EncodingData result: Create is a pure function of the specification, with no data, that analyzes the encoding of the drawn view the way Vega-Lite does - for every channel the source field, the field the marks and scales read (bin_maxbins_10_x and its _end and _range, sum_x, __count, argmax_t.v, or the end of a stack), the secondary field, the default axis or legend title lines (Sum of x, Count of Records, x (binned), merged titles of a range), the implicit bin of x and y (nice steps, maxbins of 10 by default, shared by the channels that use the same field and parameters, a discrete bin as the text of its range) and of the color, fill, stroke, size, opacity, strokeWidth, strokeDash, shape, and angle channels (maxbins of 6 by default, 4 for strokeDash, and 10 for angle), the implicit aggregate (the measures and the group-by fields of the remaining fields), and the stack (the stacked channel, the zero, center, or normalize offset, the group-by fields, and the layer order from the order channel or the stack-by fields, descending on y by default) by the StackRules of the Vega-Lite stack decision. EncodingTransforms.Apply turns a table into the EncodingData that the scales, marks, and axes read: the bins first, then the raw table, then one pass of the AggregateTransforms engine for the implicit aggregate (the input stays counted because the raw table is kept), then the stack; the raw table and the main table are the same instance unless a sort by a field or an unaggregated domain needs the raw rows. Row reservations go through the shared row budget of the DataLoader, a bin count beyond MaxScaleDomainSize or a cell or step limit is a located VegaLiteRenderException, cancellation is polled by the engines, and the result is deterministic. A channel whose own definition is a value reads the field, aggregate, bin, and title of its first condition that holds a field. Phase 8 adds the time unit: Create plans, per channel whose field has a timeUnit (and no bin or aggregate), a TimeUnitPlan (the derived start field, such as yearmonth_date, month_step_2_date, utcmonth_date, or timeunit_maxbins_10_date, and its _end companion, shared by the channels that read the same field and unit, with a band end when the mark spans its unit, and the verbal, functional, or plain default title), so that the implicit pipeline is bin, time unit, aggregate, and stack in Vega-Lite's order; EncodingTransforms.Apply runs the TimeUnitTransform unit for the plans in the time calendar of the chart and hands the resolved unit of a maxbins form on through EncodingData.TimeUnits. Phase 9 adds the polar stack (StackRules decides theta, then radius, with the dimension channel as the other of the pair, and a ranged polar mark is not stacked; the plan links theta2 and radius2 and does not group a stack by the stacked field itself), the path grouping fields (PathGroupFields, Vega-Lite's pathGroupingFields) and the order fields (OrderFields), the encoding impute of x or y (ImputePlan, the other position field as the key and the path groups as the groups, executed after the aggregate and before the stack through AggregateTransforms.ImputeField) and the implicit impute of the layers of a stacked line, area, or trail (StackImputePlan, zero for every missing stack-by group and dimension key, skipped for a binned dimension, a band end, an impute of null, and a stack without stack-by fields), all counted in the row, cell, and step budgets and cancelable. Phase 11 adds the facet part (EncodingTransforms.Facet.cs: FacetDomain, Facet, CheckFacetViews and the FacetDomains, FacetCellData, and FacetPartition records): the ordered distinct values of the row, column, and wrapped field of a facet (ascending with a null first by default and for sort null, descending, or the listed values of a sort array first and then the unlisted ones in order of appearance, a sort by an aggregate falling back to ascending), the row-major grid of every combination of a row and a column value (the combinations without rows are empty cells) or the list of the values of a wrapped facet, and one table of the rows of each cell in their original order, the number of cells computed as a long and checked against MaxViews before any row is counted, the rows counted once in the row budget, and the work charged to the step budget and cancelable. The stack and the aggregate of a view with an xOffset or yOffset channel are grouped by the offset field as well as by the dimension (the offset field splits the groups and is never a stack-by field; StackRules.DimensionOffsetChannel names the offset channel of the dimension; aggregated grouped bars are not stacked, and a quantitative offset on a view without a dimension disables the default stack). Phase 13: a facet sort by an aggregate (sort with field and op, min by default and count without a field, stable, descending with order, argmin and argmax ignored) orders the cells by the aggregate of their rows, and a timeUnit with parts on a facet field is applied with the TimeUnitTransform into a derived field whose value, the start date of the unit, is the cell; Phase 14: a bin of a facet field is the cell (its start, the range as the label), an aggregate reads the field of the name vgField gives (the facet model computes none), and a time unit of any form is applied (the maxbins form against the data, a binned unit leaving the raw value); a binned time unit of an encoding reads the field as it is and gets only the end field of a mark that spans it (TimeUnitPlan.StartPath and EndPath), and the plan names and titles bins, aggregates, and units of facet and composite grouping channels with the helpers IsBinning, AggregateFieldPath, DescribeAggregate, and DefaultFieldTitle. */

        comment sourceRef /* Source: src/DemaConsulting.CanvasNet.VegaLite/Transforms/EncodingPlan.cs, src/DemaConsulting.CanvasNet.VegaLite/Transforms/EncodingTransforms.cs, src/DemaConsulting.CanvasNet.VegaLite/Transforms/EncodingTransforms.Facet.cs */
        comment testRef /* Test: test/DemaConsulting.CanvasNet.VegaLite.Tests/Transforms/EncodingPlanTests.cs, EncodingTransformsTests.cs, EncodingPlanTimeTests.cs, EncodingTransformsTimeTests.cs, EncodingPlanPolarTests.cs, EncodingPlanPathTests.cs, EncodingTransformsImputeTests.cs, EncodingTransformsFacetTests.cs, and StackRulesOffsetTests.cs */
        comment designRef /* Design: docs/design/canvas-net-vega-lite/transforms/encoding-plan.md */
        comment verificationRef /* Verification: docs/verification/canvas-net-vega-lite/transforms/encoding-plan.md */
        comment reqRef /* Requirements: docs/reqstream/canvas-net-vega-lite/transforms/encoding-plan.yaml */
    }
}
