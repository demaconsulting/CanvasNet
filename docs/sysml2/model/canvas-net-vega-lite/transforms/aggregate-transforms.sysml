package CanvasNet {
    part def AggregateTransforms {
        doc /* The internal AggregateTransforms (a sealed partial class with the static Apply(input, entry, operation, context) entry point over a TransformContext) with its helper types AggregateMeasures and MeasureCell (the aggregate and window operation names and the accumulators), BinAlgorithm (the bin steps of the public Vega algorithm), StackRules (the Vega-Lite stack decision, with no stack on a log, pow, sqrt, or symlog scale), StableSorter (a stable merge sort), and WorkMeter (step charging): Apply runs the six grouping transforms of the drawn view eagerly over an immutable DataTable and returns a new table. aggregate groups the rows by structural keys (equal values, not equal texts) in first-seen order and writes the group fields and one measure per entry for all 24 operations (count, valid, missing, distinct, sum, product, mean, average, variance, variancep, stdev, stdevp, stderr, median, q1, q3, ci0, ci1, min, max, argmin, argmax, values, exponential, exponentialb) with Vega's value classification; ci0 and ci1 use a deterministic bootstrap seeded from the JSON pointer of the entry. joinaggregate writes the group measures to every row and keeps the row order. window adds the 13 window operations and all aggregate operations over a frame of signed offsets inside a sorted partition, with peers and an incremental path for cumulative frames. bin adds the start and end of a bin of a numeric field (default names bin0 and bin1) with the nice step selection, extent, anchor, base, divide, step, steps, and minstep options (an extent that is a parameter gives BinSettings.Span, the span of Vega-Lite's span(N[field]) that chooses the step while the bins still cover the data). stack adds the lower and upper end of the stacked value of each row (zero, center, and normalize) within the groups, ordered by sort fields. impute adds the rows of a key that a group lacks (keyvals as a list or a sequence) and replaces the missing values by a constant or by the mean, median, max, or min over a frame. The row budget of the call is shared with the DataLoader (one row per new group is reserved before it is created and an input that is no longer needed is released), MaxFieldCount, MaxStringLength, a 2^25 cell bound including the per-group measure state, the bin count (MaxScaleDomainSize), and the evaluation steps (every pass and sort is charged; sorts n times log n) are enforced with located VegaLiteRenderExceptions, cancellation is checked every 1,024 rows and during sorts and bootstraps, and there is no clock or random source, so the result is identical on every call, thread, and culture. It is also used by the EncodingPlan unit's transforms for the implicit aggregate and stack. */

        comment sourceRef /* Source: src/DemaConsulting.CanvasNet.VegaLite/Transforms/AggregateTransforms.cs, src/DemaConsulting.CanvasNet.VegaLite/Transforms/AggregateTransforms.Aggregate.cs, src/DemaConsulting.CanvasNet.VegaLite/Transforms/AggregateTransforms.Window.cs, src/DemaConsulting.CanvasNet.VegaLite/Transforms/AggregateTransforms.Bin.cs, src/DemaConsulting.CanvasNet.VegaLite/Transforms/AggregateTransforms.Stack.cs, src/DemaConsulting.CanvasNet.VegaLite/Transforms/AggregateTransforms.Impute.cs, src/DemaConsulting.CanvasNet.VegaLite/Transforms/AggregateMeasures.cs, src/DemaConsulting.CanvasNet.VegaLite/Transforms/AggregateMeasures.Cell.cs, src/DemaConsulting.CanvasNet.VegaLite/Transforms/BinAlgorithm.cs, src/DemaConsulting.CanvasNet.VegaLite/Transforms/StackRules.cs, src/DemaConsulting.CanvasNet.VegaLite/Transforms/StableSorter.cs, src/DemaConsulting.CanvasNet.VegaLite/Transforms/WorkMeter.cs */
        comment testRef /* Test: test/DemaConsulting.CanvasNet.VegaLite.Tests/Transforms/AggregateTransformsTests.cs, test/DemaConsulting.CanvasNet.VegaLite.Tests/Transforms/AggregateTransformsJoinAggregateTests.cs, test/DemaConsulting.CanvasNet.VegaLite.Tests/Transforms/AggregateTransformsWindowTests.cs, test/DemaConsulting.CanvasNet.VegaLite.Tests/Transforms/AggregateTransformsStackTests.cs, test/DemaConsulting.CanvasNet.VegaLite.Tests/Transforms/AggregateTransformsImputeTests.cs, test/DemaConsulting.CanvasNet.VegaLite.Tests/Transforms/AggregateMeasuresTests.cs, test/DemaConsulting.CanvasNet.VegaLite.Tests/Transforms/BinAlgorithmTests.cs, test/DemaConsulting.CanvasNet.VegaLite.Tests/Transforms/StackRulesTests.cs, test/DemaConsulting.CanvasNet.VegaLite.Tests/Transforms/StableSorterTests.cs, test/DemaConsulting.CanvasNet.VegaLite.Tests/Transforms/AggregateTestSupport.cs */
        comment designRef /* Design: docs/design/canvas-net-vega-lite/transforms/aggregate-transforms.md */
        comment verificationRef /* Verification: docs/verification/canvas-net-vega-lite/transforms/aggregate-transforms.md */
        comment reqRef /* Requirements: docs/reqstream/canvas-net-vega-lite/transforms/aggregate-transforms.yaml */
    }
}
