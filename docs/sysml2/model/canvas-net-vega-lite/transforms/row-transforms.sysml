package CanvasNet {
    part def RowTransforms {
        doc /* The internal RowTransforms (a sealed partial class with the static Apply(input, transforms, context) entry point over a TransformContext that carries the SpecTree with its compiled expressions, the DataLoader of the call, the ExpressionEvaluator, the parameter values, the limits, the cancellation token, and the list that receives the warnings) with the RowSampler, TableLayout and FieldReader, ParameterEnvironment and SpecValues, and RowExpressions types: Apply runs the transforms of the drawn view in order and returns the input table itself when there is none, delegating aggregate, joinaggregate, window, bin, stack, and impute to the AggregateTransforms unit and, since Phase 13, the regression, loess, density, quantile, and extent transforms to the StatTransforms unit. calculate evaluates the expression once per row with the row as datum and stores any value kind (scalar, array, object; a regular expression becomes null with the warning vl-expr-runtime), with literal as names; filter keeps the rows with a truthy expression or a true predicate (JavaScript truthiness and relational rules; range inclusive with a null bound open; valid is not null and not NaN; param is the truthiness of a variable parameter, or, for a selection parameter, the expression that Vega-Lite compiles for it - the selection test with its empty rule - evaluated for every row by the expression engine over the selection stores), composing and, or, and not; fold emits one row per folded field (key and value, null for a missing field); flatten rebuilds arrays from the flattened fields and expands them in parallel with null padding; sample uses RowSampler (FNV-1a 64-bit of the UTF-8 JSON pointer, SplitMix64, algorithm R, indexes restored to source order, a stable copy when the size is at least the count); pivot groups in first-seen order into ordinal columns of any aggregate operation (the cells of the AggregateTransforms unit, with the empty cell of Vega: no value for a sum, 0 for a count) with limit; lookup indexes the secondary source loaded by the DataLoader of the call by the text of the key and copies the fields of the first match (default value null, a whole-row object when no fields are named). TableLayout lays out the derived tables (fields in ordinal order, an added field replacing the fields nested below it, MaxFieldCount, a 2^25 cell bound) and FieldReader rebuilds arrays and objects from the flattened cells. ParameterEnvironment evaluates the static variable parameters in the dependency order the SpecParser's ParameterGraph produced (an expression wins over a value; a render option replaces the whole definition, and a caller's value can be a scalar, an array, or an object) and, since Phase 12 (milestone 1), runs first in each call, hoisted out of the data stage into VegaLiteDocument.PrepareChart so that the expression references of the static sites are folded from the same values; only the variable parameters of the top-level view exist and SpecValues converts a JSON value to a DataValue. The row budget is shared with the DataLoader (ReserveDerivedRows before allocating, ReleaseRows after the input is no longer needed); limit failures are VegaLiteRenderExceptions located at the transform, expression, or lookup source; warnings are vl-expr-runtime and vl-transform-runtime (pivot rows with a null pivot value skipped, columns cut at limit); cancellation is checked at the start of every transform and at least every 1,024 rows. Phase 8 dispatches the timeUnit transform to the TimeUnitTransform unit with the time calendar of the chart (the evaluator's calendar), and evaluates a filter or condition predicate that has a time unit or a datetime object through the expression that the SpecParser compiled for it (RowTransforms.Predicates.cs), in the time zone of the chart, charging the work of the expression to the step budget. */

        comment sourceRef /* Source: src/DemaConsulting.CanvasNet.VegaLite/Transforms/RowTransforms.cs, src/DemaConsulting.CanvasNet.VegaLite/Transforms/RowTransforms.Predicates.cs, src/DemaConsulting.CanvasNet.VegaLite/Transforms/RowTransforms.Shape.cs, src/DemaConsulting.CanvasNet.VegaLite/Transforms/RowTransforms.Lookup.cs, src/DemaConsulting.CanvasNet.VegaLite/Transforms/RowSampler.cs, src/DemaConsulting.CanvasNet.VegaLite/Transforms/TableLayout.cs, src/DemaConsulting.CanvasNet.VegaLite/Transforms/ParameterEnvironment.cs, src/DemaConsulting.CanvasNet.VegaLite/Transforms/TransformContext.cs, src/DemaConsulting.CanvasNet.VegaLite/Transforms/NamespaceDoc.cs */
        comment testRef /* Test: test/DemaConsulting.CanvasNet.VegaLite.Tests/Transforms/RowTransformsTests.cs and RowTransformsTimeTests.cs */
        comment designRef /* Design: docs/design/canvas-net-vega-lite/transforms/row-transforms.md */
        comment verificationRef /* Verification: docs/verification/canvas-net-vega-lite/transforms/row-transforms.md */
        comment reqRef /* Requirements: docs/reqstream/canvas-net-vega-lite/transforms/row-transforms.yaml */
    }
}
