package CanvasNet {
    part def DataFileResolver {
        doc /* The internal DataFileResolver (a sealed class) and the DataFile record it returns: a thin layer over the core FileReferenceResolver that finds and reads the local data files that a chart names with a local data url (relative, absolute, a drive path, or the local path of a file: URI without a host, which Load(path, location, written) names as written), once per measure or render call, under the file-access policy of VegaLiteOpenOptions.FileAccess (AllowAll by default: dot-dot, absolute paths and symbolic links are followed). The core engine searches the base directory and then each data path in order (search locations, not boundaries; an absolute path names one file), or, with the caller's file callback, never touches the file system or the policy and hands the callback only normalized logical paths (an absolute path is then a located error); it rejects empty, control-character, network, device and alternate-data-stream paths under every policy, refuses a handle that is not a regular file, fails closed when a restrictive policy needs a real path that cannot be determined, asks the policy about the real path of the open handle, reads bytes under MaxDataBytes and MaxDataFiles (an endless stream stops one chunk past the limit) and opens files read-only with shared access; a dangling link is a missing file; environment variables and the current directory are never consulted. This unit adds strict UTF-8 decoding with the byte-order mark removed, a decoded-file cache for the call, and the translation of every one of the eleven FileReferenceFailureKind values into a VegaLiteRenderException located at the data url with Vega-Lite wording and the FileReferenceException as its inner exception (a denial reads "The data file '...' was denied by the file-access policy '...': reason.", naming the url as written, never a host directory). A missing, denied, unreadable (an existing file whose open fails, which is never reported as missing, a directory in place of a file, or a callback or callback stream that throws or fails to dispose), invalid, or oversized file is a VegaLiteRenderException, never an empty result; cancellation passes through unchanged. Remote URLs never reach it. */

        comment sourceRef /* Source: src/DemaConsulting.CanvasNet.VegaLite/Data/DataFileResolver.cs */
        comment testRef /* Test: test/DemaConsulting.CanvasNet.VegaLite.Tests/Data/DataFileResolverTests.cs, test/DemaConsulting.CanvasNet.VegaLite.Tests/Data/DataFileResolverLinkTests.cs, test/DemaConsulting.CanvasNet.VegaLite.Tests/Data/DataTestSupport.cs */
        comment designRef /* Design: docs/design/canvas-net-vega-lite/data/data-file-resolver.md */
        comment verificationRef /* Verification: docs/verification/canvas-net-vega-lite/data/data-file-resolver.md */
        comment reqRef /* Requirements: docs/reqstream/canvas-net-vega-lite/data/data-file-resolver.yaml */
    }
}
