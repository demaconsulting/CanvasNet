package CanvasNet {
    part def DataTable {
        doc /* The internal DataTable (a sealed immutable class) with the DataValueKind enumeration, the DataValue readonly struct, and the JsNumber and FieldPath static classes: DataValue holds a null, boolean, number, date, or string with SameValueZero equality (so it can be a dictionary key), a total ordering (null, boolean, number, date, string), TryGetQuantitative (numbers, dates as milliseconds, booleans as 1 and 0, and numeric strings), and ToText (JavaScript String semantics; a date as ISO 8601 in UTC with milliseconds); a date is an instant in UTC held as milliseconds since the epoch (years 1 to 9999, created from milliseconds or a DateTime, never dependent on the host time zone); JsNumber reproduces JavaScript number-to-text conversion with the shortest round-trip digits, parsing, rounding, and radix conversion; FieldPath parses, joins, escapes, and canonicalizes Vega field paths (dotted, bracketed, quoted, and escaped); DataTable keeps its canonical field names in ordinal order and its cells row by row, is built by Create (a field list and rows) or FromRecords (dictionaries, with the union of the keys and null for a missing value) under MaxDataRows and MaxFieldCount (VegaLiteRenderException with the supplied location), and offers IndexOfField, FindField, typed GetValue, GetNumber, GetString, and GetBoolean accessors, GetRow, and Column. Phase 5 extends the DataValue model additively: the kinds Array, Object, and RegExp (FromArray copies its elements, FromObject takes an immutable DataObject with its keys in insertion order and the last value of a repeated key, FromRegExp carries an opaque payload) hold the results of expressions and the cells of derived tables, compare by identity, format like JavaScript, and sort after every scalar without changing the order of the scalars; the DataObject and DataArray types are in DataObject.cs; FromSortedCells builds a derived table directly from a sorted field list and row-major cells under MaxDataRows and MaxFieldCount. */

        comment sourceRef /* Source: src/DemaConsulting.CanvasNet.VegaLite/Data/DataTable.cs, src/DemaConsulting.CanvasNet.VegaLite/Data/NumericConversions.cs, src/DemaConsulting.CanvasNet.VegaLite/Data/DataObject.cs, src/DemaConsulting.CanvasNet.VegaLite/Data/NamespaceDoc.cs */
        comment testRef /* Test: test/DemaConsulting.CanvasNet.VegaLite.Tests/Data/DataTableTests.cs, test/DemaConsulting.CanvasNet.VegaLite.Tests/Data/DataCompositeValueTests.cs, test/DemaConsulting.CanvasNet.VegaLite.Tests/Data/NumericConversionsTests.cs */
        comment designRef /* Design: docs/design/canvas-net-vega-lite/data/data-table.md */
        comment verificationRef /* Verification: docs/verification/canvas-net-vega-lite/data/data-table.md */
        comment reqRef /* Requirements: docs/reqstream/canvas-net-vega-lite/data/data-table.yaml */
    }
}
