package CanvasNet {
    part def DelimitedTextParser {
        doc /* The internal static DelimitedTextParser with ParseDirectives, ParseFailures, and the DelimitedOptions and DelimitedResult records: it reads delimiter-separated text (CSV with a comma, TSV with a tab, DSV with the single character a format names) into rows of typed values. The first record is the header (names stored as canonical field names); a quoted field may hold delimiters, line breaks, and doubled quotes; line feed, carriage return plus line feed, and lone carriage return end a record; empty lines, a missing final line end, and a leading byte-order mark are accepted; a short row has null in the missing fields and extra entries are ignored (they are read and validated but never stored, and a header is refused as soon as it exceeds the field limit); malformed quoting, a repeated or too many header names, an over-long text, and more rows than the budget are located VegaLiteRenderExceptions. ParseDirectives applies the parse property of a data format: no conversion unless asked (an absent or null parse keeps delimited cells as strings, as in Vega), inference per column only for an explicit auto (boolean, then number, then date, only when every non-empty text of the column fits, an empty cell null in a typed column, and only text within the supported date range of the years 1 to 9999 counts as a date), and an explicit map converts only the named fields to number, boolean, date, or string, making a value that cannot be converted (including ISO text beyond the supported date range) null and counting it in ParseFailures (one vl-data-parse-failed warning per field and type); custom date formats are applied (date with a d3 time format in the zone of the chart, utc with one in UTC); a plain date conversion and the inference read dates by the JavaScript Date.parse rules (JsDateParser; a text with only a date is UTC and a date-time without a zone a time of the chart's zone), the fields that the specification uses as dates are converted implicitly unless the parse property names them or is null, and cancellation is polled every 4,096 rows of a column. Its delimiter rule and parse-entry classification are shared with SpecParser and FeatureCatalog. Cancellation is polled every 1,024 records. */

        comment sourceRef /* Source: src/DemaConsulting.CanvasNet.VegaLite/Data/DelimitedTextParser.cs */
        comment testRef /* Test: test/DemaConsulting.CanvasNet.VegaLite.Tests/Data/DelimitedTextParserTests.cs and ParseDirectivesDateTests.cs */
        comment designRef /* Design: docs/design/canvas-net-vega-lite/data/delimited-text-parser.md */
        comment verificationRef /* Verification: docs/verification/canvas-net-vega-lite/data/delimited-text-parser.md */
        comment reqRef /* Requirements: docs/reqstream/canvas-net-vega-lite/data/delimited-text-parser.yaml */
    }
}
