package CanvasNet {
    part def DataLoader {
        doc /* The internal DataLoader (a sealed class, one instance per measure or render call, plus a static Load for inline data and sequences only): Load reads the data of a view from its data property and returns a DataTable. The source is chosen by precedence - inline values given as an array (an array of objects gives one row per object; an array of primitives gives one row per value in the field data; JSON types are kept; a nested object or array is flattened to leaf fields named by their canonical path, and a field a row lacks is null), then a local url (relative, absolute, a drive path, or a file: URI without a host, which is read at its local path through FeatureCatalog.LocalPathOfFileUri and named in messages as written) read through DataFileResolver under the file-access policy of the open options as JSON (the default), CSV, TSV, or DSV (format.type, else the .csv or .tsv extension; format.property selects the rows of a JSON file), then a sequence (start and stop must be finite numbers, step is 1 only when absent and otherwise a finite nonzero number, exclusive stop, as; a step pointing away from the stop is empty and an overflowing length fails MaxDataRows before allocation), then a name (the caller's datasets before the top-level datasets of the specification). format.parse is applied to every source (as in Vega, no inference unless parse is auto: delimited text keeps its cells as strings by default, and a parse map converts the named fields only) and the values that an explicit conversion cannot read are exposed as vl-data-parse-failed warnings. A caller's DateTime and DateTimeOffset values become UTC dates, with the largest values of both types (the usual no-end sentinels) clamped to the last supported millisecond of the year 9999. A url that FeatureCatalog.IsRemoteDataUrl classifies as remote (a scheme of two or more characters other than file, a file: URI with a host or a malformed one, or a path that starts with two slashes or backslashes) is remote: the table is empty, nothing is resolved or fetched, and the FeatureCatalog reports vl-data-remote-url; text or object values, a topojson format, and no source are also empty tables reported by the catalog. A local file that is missing or cannot be used, an undefined name, invalid JSON (including text that is not valid Unicode, such as an escaped lone surrogate) or delimited text, or a limit (MaxDataRows as a total across the tables of the call and checked before any row is converted or allocated, MaxFieldCount, MaxStringLength, and, through the resolver, MaxDataFiles and MaxDataBytes) throws a VegaLiteRenderException with the location of the offending data in lenient and strict mode alike; cancellation is checked every 1,024 rows. Phase 5 makes the loader the context of the row transforms: the secondary source of a lookup is loaded by Load on the same instance (so with the file-access policy, the file cache, the file and byte limits, and the row total of the main data), ReserveDerivedRows counts the rows of a derived table against MaxDataRows before it is allocated, and ReleaseRows gives back the rows of a table that is no longer needed. Phase 8 gives the loader the time calendar of the chart (a constructor parameter, UTC when none is given) and the set of the fields that the specification uses as dates (a parameter of Load for the main data only, never for the secondary source of a lookup), and passes both to every date conversion of the delimited, JSON, inline, caller-supplied, and specification sources. */

        comment sourceRef /* Source: src/DemaConsulting.CanvasNet.VegaLite/Data/DataLoader.cs */
        comment testRef /* Test: test/DemaConsulting.CanvasNet.VegaLite.Tests/Data/DataLoaderTests.cs */
        comment designRef /* Design: docs/design/canvas-net-vega-lite/data/data-loader.md */
        comment verificationRef /* Verification: docs/verification/canvas-net-vega-lite/data/data-loader.md */
        comment reqRef /* Requirements: docs/reqstream/canvas-net-vega-lite/data/data-loader.yaml */
    }
}
