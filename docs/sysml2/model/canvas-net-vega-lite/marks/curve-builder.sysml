package CanvasNet {
    part def CurveBuilder {
        doc /* The internal CurveBuilder (a static class in three partial files) of the Marks subsystem: the interpolation of the paths of the line, area, and trail marks. CurveKind names the sixteen curves (linear, linear-closed, step, step-before, step-after, basis, basis-open, basis-closed, bundle, cardinal, cardinal-open, cardinal-closed, catmull-rom, monotone-x, monotone-y, and natural); TryParse accepts exactly the fifteen Vega-Lite interpolate names (monotone becomes monotone-y for a horizontal area; catmull-rom-open and catmull-rom-closed, which are Vega-only, are refused). Line and Area are literal ports of the d3-shape curve classes and of the d3-shape line and area generators with their defined predicate: each curve writes absolute move, line, cubic, and close segments (ScenePathSegment) through a sink that emulates d3-path, a point that is undefined or has a coordinate that is not finite starts a new subpath, an area writes the top edge forward and the baseline backward through the same curve (the area start and end passes, the toggling of the line flag), and the bundle curve, which has no area in d3-shape, is reported by SupportsArea and refused by Area so that the caller falls back to the linear curve. The tension applies to the bundle (beta), cardinal (tension), and catmull-rom (alpha) curves; a non-finite tension counts as absent. MaxSegments gives, before anything is generated, an upper bound of the number of segments of a path (a factor for the curve times the defined points, doubled for an area, plus the runs) that saturates at the largest long, so that MarkBuilder charges the scene budget first, and the generators poll the cancellation token at the first point and then every 1,024 points. The unit has no state, no clock, and no culture dependency; every coordinate it emits is finite. */

        comment sourceRef /* Source: src/DemaConsulting.CanvasNet.VegaLite/Marks/CurveBuilder.cs, src/DemaConsulting.CanvasNet.VegaLite/Marks/CurveBuilder.Splines.cs, src/DemaConsulting.CanvasNet.VegaLite/Marks/CurveBuilder.Generators.cs */
        comment testRef /* Test: test/DemaConsulting.CanvasNet.VegaLite.Tests/Marks/CurveBuilderTests.cs, test/DemaConsulting.CanvasNet.VegaLite.Tests/Marks/CurveBuilderSplineTests.cs, test/DemaConsulting.CanvasNet.VegaLite.Tests/Marks/CurveBuilderAreaTests.cs */
        comment designRef /* Design: docs/design/canvas-net-vega-lite/marks/curve-builder.md */
        comment verificationRef /* Verification: docs/verification/canvas-net-vega-lite/marks/curve-builder.md */
        comment reqRef /* Requirements: docs/reqstream/canvas-net-vega-lite/marks/curve-builder.yaml */
    }
}
