package CanvasNet {
    part def MarkBuilder {
        doc /* The internal MarkBuilder (a sealed partial class) with IsSupported (true for bar, rect, point, circle, square, rule, tick, line, area, trail, text, arc, and image) and Build, which reads the mark type (a string or the type of a mark definition), loops over the rows of the DataTable (cancellation polled every 1,024 rows, the scene budget charged for the marks group and each item before it is created), maps the channels x, y, color, fill, stroke, size, opacity, shape, strokeWidth, strokeDash, fillOpacity, strokeOpacity, and angle through the scale models (field, value, and datum forms), resolves the mark properties through the ResolvedConfig precedence chain, and creates the SceneRect, SceneSymbol, and SceneRule items of a marks group in the coordinates of the data rectangle: bars, rectangles, and ticks fill the band on a discrete position (at least minBandSize; step minus 2 on a point scale) and are centered with continuousBandSize or thickness on a continuous one, the measure axis runs from the value to zero (or, for a stacked channel and for an x2 or y2 range, from the start to the end), symbols sit at the band center or the value with the size as the area of the bounding box (at the upper end of a stack), and rules are full-width or full-height lines, stems to zero, or segments of a range; Phase 6 draws the stacked layers of the EncodingPlan from the start to the end value of each row, the x2 and y2 secondary channels of bar, rect, and rule marks (a field, a datum, or a pixel value; a row with an invalid end is not drawn), a bar or rect on a binned channel as the span of its bin less binSpacing (bar 1, rect and tick 0) with a half-pixel edge and a minimum of minBandSize, the bin midpoint for point-like marks, and the clip of the data rectangle when the x or y scale has an explicit array domain (unless clip is false); paint follows Vega-Lite (the mark color is the fill of a filled mark and the stroke of an unfilled one, colors from the ordinal, sequential, diverging, quantize, quantile, or threshold scale of the channel, default opacity 0.7 for point, circle, square, and tick). Phase 7 gives each row its stroke width, fill opacity, stroke opacity, and dash pattern (at most 64 entries; a longer one is a located VegaLiteRenderException) from the strokeWidth, fillOpacity, strokeOpacity, and strokeDash channels, and each point its shape (a symbol name; a custom path is kept and drawn as a circle) and each point, circle, or square its angle; a channel that the mark does not draw (shape, angle, strokeDash) is ignored. A row with a null, NaN, or non-numeric value on a channel with a continuous domain is not drawn. Exceeding MaxSceneItems is a VegaLiteRenderException with the location of the mark, and cancellation is polled every 1,024 rows. Phase 5 gives the constructor an optional RowExpressions (the compiled expressions and the evaluator of the call): the expr references of the drawn view's mark color, fill, stroke, opacity, strokeWidth, and size (point, circle, and square) and of the constant value of the color, fill, stroke, opacity, and size (point, circle, and square) channels are evaluated once per row against the transformed row, a text result being a color and a finite number an opacity, width, or size, any other result leaving the default; the tests of conditions are evaluated as described below and every other expression site is ignored (and reported by the FeatureCatalog). A row whose value a log, pow, sqrt, or symlog scale cannot map (zero on a log scale) has no position and is not drawn, and the bars of a log axis start at the start of the domain. A binned field draws each mark with the value of its scale at the start of the bin (the color of the bin of a bin-ordinal scale), and the bars of a histogram whose color bins the field as x does take the color of their bin. The test of every condition of a color, fill, stroke, opacity, fill opacity, stroke opacity, stroke width, stroke dash, size, shape, or angle channel is evaluated for every row by the expression engine under the step budget, the first condition that holds gives the value (or the scaled field), and a row for which none holds gets the value or scale of the channel or the default of the mark. Phase 8 draws the bar or rect of a field with a time unit on a time scale over its whole unit (from the start field to the end field of the plan, edges at lerp(start, end, (1 - band) / 2) and (1 + band) / 2 with band the relative width or timeUnitBandSize, the bar spacing, the minimum band size compared with the whole unit, and the half-pixel axis translate as for a bin), places the points, circles, squares, ticks, and rules of a time unit at lerp(start, end, bandPosition) (the start when no band position is defined, the middle for the ticks and bars by the default configuration), draws a rect-based mark whose band position is not one half at one half (the FeatureCatalog reports vl-encoding-bandposition-rect), and places the marks of a time scale at their dates. Phase 9 (MarkBuilder.Order.cs, MarkBuilder.Paths.cs, MarkBuilder.Overlays.cs, MarkBuilder.Text.cs, and MarkBuilder.Arcs.cs, partial files of the MarkBuilder and of its Run) makes IsSupported true for line, area, trail, text, and arc as well. A line, an area, or a trail is built from groups: the rows are read once (validity of the continuous channels, pixel positions kept even for an invalid row), counted into groups of equal values of EncodingPlan.PathGroupFields in the order of the first row, and each group is sorted stably by the order fields or the pixel position of the dimension, painted from its first defined row, charged to the scene budget (one item and the CurveBuilder.MaxSegments bound) before its segment list exists, and emitted as one ScenePath with segments (line: stroke, size as the stroke width; area: closed outline between the value and the baseline, the start of the stack, or the second channel, vertical or horizontal by the orient) or one SceneTrail with runs of points that carry the per-point size; the interpolate and tension properties choose the curve (an area with bundle falls back to linear), the invalid mode (default break-paths-show-path-domains) breaks the path at an invalid row or, for filter, connects the neighbors (a row whose value on a stacked channel is not a number counts as 0 in the stack and is then invalid: a bar, arc, symbol, or label of it is not drawn and a stacked area breaks its path), and a group with fewer than two defined points draws nothing and costs nothing. The overlays are built by a second run with the overlay definition (point symbols on line, area, trail, and rule; a line on the top edge of an area; the 0.7 default opacity of an area with an overlay). The text mark creates one SceneText per row with the formatted label (d3 number and time formats through TimeLabels, bin ranges, JavaScript text, array and lineBreak lines, a limit of MaxStringLength per label and sixteen times that per mark), the Vega defaults, the font, angle, and offsets, and the polar offset of theta and radius. The arc mark creates one SceneArc per row from the theta and radius scales (stacked slices from the start to the end of the stack, a band scale across its band, the mark properties theta, theta2, radius, radius2, innerRadius, outerRadius, padAngle, and cornerRadius) around the center of the data rectangle or the x and y position. The order channel sorts the draw order of every other mark when the encoding is not stacked, and the dash, dash offset, cap, join, and miter limit reach every item type. The xOffset and yOffset channels (MarkBuilder.Offsets.cs: ChannelOffset, AttachOffsets, and OffsetCenter, hooked into Center and BandSpan) place the marks inside the band of their group: a point-like mark (point, circle, square, text, line, area) sits at the start of the band of the position plus the center of the offset scale (a continuous offset draws a strip inside the band, as a jitter), a bar, rect, tick, or rule spans the band of the offset scale (an explicit size is centered in it), the stack is made inside each group of the offset only, and a row whose offset value is invalid is not drawn; for a temporal position with a time unit (TimeUnitOffsetRange) the marks read the time scale at the start of the unit and add the offset, the range of the offset scale being one reference unit of the time scale (the pixels between the start and the end of ReferenceSpan, a month being the 31 days of January 2001, negative on a y scale) inset by config.scale.bandWithNestedOffsetPaddingInner and moved by the band position (the band position of the channel, else the time unit band position, else one half), a bar spanning a band of the offset scale scaled by the time unit band size unless it has a size (BandSpan). Phase 12 (milestone 1) clips the marks group to the data rectangle also when the x or y scale takes its domain from a parameter (ClipMarks), not only for a mark definition with clip true. Phase 12 (milestone 2b, MarkBuilder.Brush.cs) builds the brush marks of an interval selection that has an initial value: a selection-brush-background group (fill #333 at the fill opacity 0.125) before and a selection-brush group (transparent with a white stroke) after the marks, clipped, whose rectangle is the min and the absolute difference of the mapped ends of the first tuple of the store (the start of the band on a band scale, the data rectangle on a channel the selection does not project), with the mark of config.selection.interval.mark merged under the mark of the selection; the owner unit only under resolve global, never a facet cell, none for a scale-bound selection, and no rectangle with no area. Phase 13 (MarkBuilder.Images.cs) draws the image mark as one SceneImage (role mark-image) per row that has a link (the url channel as a field, datum, or value, else the url property of the mark; a value as its JavaScript text; a null or empty link draws nothing): each axis follows Vega-Lite rectPosition for the image mark, a point anchored by the align or baseline of the mark (center and middle) when the axis has a position and no size or second end, the bin of a binned field, the band of a discrete scale or a width centered in it, a range from the value to x2 (or the zero of the scale) or a width or height of the mark aligned at the position, and, for an absent channel, the whole data rectangle (or a size anchored at the right edge or the top); the aspect and smooth properties (true) and the opacity (1) are carried, each row charges one scene item and a link longer than MaxStringLength is a located VegaLiteRenderException. The picture is never loaded by the builder. Phase 13 draws the show invalid mode (and null): ApplyShowInvalid gives each channel with a field and a continuous domain a fallback data value for a value that is not a number, the scale output of zero when the domain contains zero (not on a time, UTC, or log scale) and else of the first value of the domain (Vega-Lite scaledZeroOrMinOrMax), so the row is drawn at zero or at the minimum; a stacked null row is drawn at its stack position and a stacked channel ignores config.scale.invalid. In Phase 14 a channel that has an entry in config.scale.invalid ("zero-or-min" or {"value": number or text}; Vega-Lite 6.5 invalid.ts) is in the show mode whatever the invalid mode of the mark is: its null, NaN, and non-finite rows are not filtered and do not break a path, "zero-or-min" places them where the scale maps zero (else the first domain value) and a value is the output of the channel as it is (ScaleModel.WithInvalidOutput); the other channels keep the mode of the mark and an unreadable entry is ignored. A bar or an area whose position is a band scale with a ranged offset (ChannelOffset.Ranged and Range, ScaleResolver.HasRangedOffset: an unbinned quantitative xOffset or yOffset, Vega-Lite isRangedOffset) spans inside the band from the zero of the offset scale to the offset value (RangePair and Span; a negative value hangs on the other side of the baseline) and the measure axis of an area follows the ranged offset. A custom SVG path shape of a point is kept as written and drawn by the SymbolPathParser. */

        comment selectionRef /* Phase 12 (milestone 2): a condition on a param (a selection or a variable parameter) or a legacy selection is evaluated for every row as the predicate that the parser compiled for it (the selection test of Vega-Lite with its empty rule over the stores of the call), in order with the conditions on a test; the field of such a condition gives the scale and legend of the channel. */
        comment sourceRef /* Source: src/DemaConsulting.CanvasNet.VegaLite/Marks/MarkBuilder.cs, src/DemaConsulting.CanvasNet.VegaLite/Marks/MarkBuilder.Order.cs, src/DemaConsulting.CanvasNet.VegaLite/Marks/MarkBuilder.Paths.cs, src/DemaConsulting.CanvasNet.VegaLite/Marks/MarkBuilder.Overlays.cs, src/DemaConsulting.CanvasNet.VegaLite/Marks/MarkBuilder.Text.cs, src/DemaConsulting.CanvasNet.VegaLite/Marks/MarkBuilder.Arcs.cs, src/DemaConsulting.CanvasNet.VegaLite/Marks/MarkBuilder.Images.cs, src/DemaConsulting.CanvasNet.VegaLite/Marks/MarkBuilder.Offsets.cs, src/DemaConsulting.CanvasNet.VegaLite/Marks/MarkBuilder.Brush.cs, src/DemaConsulting.CanvasNet.VegaLite/Marks/NamespaceDoc.cs */
        comment testRef /* Test: test/DemaConsulting.CanvasNet.VegaLite.Tests/Marks/MarkBuilderTests.cs, test/DemaConsulting.CanvasNet.VegaLite.Tests/Marks/MarkBuilderChannelTests.cs, test/DemaConsulting.CanvasNet.VegaLite.Tests/Marks/MarkBuilderConditionTests.cs, test/DemaConsulting.CanvasNet.VegaLite.Tests/Marks/MarkBuilderTimeTests.cs, test/DemaConsulting.CanvasNet.VegaLite.Tests/Marks/MarkBuilderPathTests.cs, test/DemaConsulting.CanvasNet.VegaLite.Tests/Marks/MarkBuilderOrderTests.cs, test/DemaConsulting.CanvasNet.VegaLite.Tests/Marks/MarkBuilderOverlayTests.cs, test/DemaConsulting.CanvasNet.VegaLite.Tests/Marks/MarkBuilderTextTests.cs, test/DemaConsulting.CanvasNet.VegaLite.Tests/Marks/MarkBuilderArcTests.cs, test/DemaConsulting.CanvasNet.VegaLite.Tests/Marks/MarkBuilderPolarTextTests.cs, test/DemaConsulting.CanvasNet.VegaLite.Tests/Marks/MarkBuilderImageTests.cs, test/DemaConsulting.CanvasNet.VegaLite.Tests/Marks/MarkBuilderOffsetTests.cs, test/DemaConsulting.CanvasNet.VegaLite.Tests/Marks/MarkBuilderInvalidShowTests.cs, test/DemaConsulting.CanvasNet.VegaLite.Tests/Marks/MarkBuilderScaleInvalidTests.cs, test/DemaConsulting.CanvasNet.VegaLite.Tests/Marks/MarkBuilderRangedOffsetTests.cs, test/DemaConsulting.CanvasNet.VegaLite.Tests/VegaLiteBrushIntegrationTests.cs */
        comment designRef /* Design: docs/design/canvas-net-vega-lite/marks/mark-builder.md */
        comment verificationRef /* Verification: docs/verification/canvas-net-vega-lite/marks/mark-builder.md */
        comment reqRef /* Requirements: docs/reqstream/canvas-net-vega-lite/marks/mark-builder.yaml */
    }
}
