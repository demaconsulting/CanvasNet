package CanvasNet {
    part def Ticks {
        doc /* The internal static Ticks, a port with attribution of the d3-array tick algorithms and the d3-scale linear nice method plus the tick-count rules of Vega and Vega-Lite: GetTicks, TickIncrement (d3's signed encoding, in which a negative value stands for the reciprocal of the step, which keeps the arithmetic exact), and TickStep choose evenly spaced ticks that are 1, 2, or 5 times a power of ten with the thresholds sqrt(50), sqrt(10), and sqrt(2); Nice extends a domain to nice boundaries (at most ten rounds until the step settles, direction kept, unchanged when it does not settle); DefaultAxisTickCount is Vega-Lite's one tick per 40 pixels, DefaultAxisTickMinStep is 1 for the integer format d, ResolveTickCount is Vega's tickCount that lowers the count until the step reaches the minimum step, and AxisTicks combines them. A result of more than MaxTicks values is a VegaLiteRenderException thrown before the array is allocated; inputs that are not numbers give an empty array or an unchanged domain. ModelTicks dispatches by the transform of a scale model (the ordinary ticks for linear, pow, sqrt, and symlog, as in d3), LogTicks is the ticks method of d3's scaleLog (the multiples of every power inside the domain, the d3 ticks of the exponents for a wide domain, reflected for a domain below zero, bounded by MaxTicks and a work limit of a hundred times it, polling the cancellation token), LogNice floors and ceils a log domain to powers of the base, LogLabelTest is the label filter of Vega's tickLog (max(1, base * count / ticks) on the leading digit, judged on the magnitude), and ResolveTickCount does not lower the count by the step for a log scale. Phase 8 (Ticks.Time.cs) adds the time ticks of d3-time and d3-scale over the TimeCalendar: TimeTickInterval chooses the interval of the d3 table (1, 5, 15, and 30 seconds and minutes; 1, 3, 6, and 12 hours; 1 and 2 days; 1 week; 1 and 3 months; 1 year, the nearest to the target by the d3 rule, the tick step for years and milliseconds), TimeTicks lists the ticks of a time or UTC scale (inclusive stop, a reversed domain reversed, the boundaries of the zone, the two-day ticks of a UTC scale counted from the epoch, and the explicit interval or interval and step of a TimeTickRequest) bounded by MaxTicks with a VegaLiteRenderException and polling the cancellation token, TimeNice floors and ceils a time domain to the interval, and ResolveTickCount skips the tick step shrink loop for a temporal scale. */

        comment sourceRef /* Source: src/DemaConsulting.CanvasNet.VegaLite/Scales/Ticks.cs and Ticks.Time.cs */
        comment testRef /* Test: test/DemaConsulting.CanvasNet.VegaLite.Tests/Scales/TicksTests.cs and TicksTimeTests.cs */
        comment designRef /* Design: docs/design/canvas-net-vega-lite/scales/ticks.md */
        comment verificationRef /* Verification: docs/verification/canvas-net-vega-lite/scales/ticks.md */
        comment reqRef /* Requirements: docs/reqstream/canvas-net-vega-lite/scales/ticks.yaml */
    }
}
