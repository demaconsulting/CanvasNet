package CanvasNet {
    part def ScaleModel {
        doc /* The internal ScaleModel (a sealed immutable class), the ScaleRange struct (texts, numbers, or only a count), and the ScaleKind enumeration (Linear, Band, Point, Ordinal, Sequential, Diverging, Quantize, Quantile, Threshold, BinOrdinal, Time, Utc): the pure arithmetic of scales with no knowledge of the specification, a port of the d3-scale and Vega behavior with attribution. CreateLinear, CreateBand, CreatePoint, CreateOrdinal, CreateSequential (two entries sequential, three diverging), CreateQuantize, CreateQuantile, CreateThreshold, and CreateBinOrdinal build the models; Map maps a number or data value (a linear value through normalize and interpolate with clamp, round, reversed domain or range, and d3 piecewise (polymap and bimap) mapping for a domain and range of more than two entries, using min(domain length, range length) entries; a band or point value to the start of its band or its position; the numbers of an ordinal or discretizing scale; null for a value outside the domain), MapCenter gives the center of a band, MapOrdinal cycles through the range, MapText gives the text (color or shape) of any ordinal, discretizing, sequential, or diverging scale, MapColor the color of a number through an interpolator (d3 scaleSequential position (x - x0) / (x1 - x0), d3 scaleDiverging position 0.5 + (x - x1) * k with the slope of the side of the middle value), MapIndex the position in the range (quantize, quantile, and threshold intervals by bisectRight over the thresholds, Vega's bin-ordinal index modulo the range), Invert and IndexOf give the inverse mappings, and BandSpace is Vega's bandspace rule. A linear domain of zero width maps to the middle of the range, NaN maps to NaN, and calling an operation of another kind of scale is an InvalidOperationException. A linear, sequential, or diverging model can carry a ScaleTransform (ScaleTransformKind Linear, Log, Pow, Symlog, with the base, exponent, or constant): the value is clamped in the domain, transformed (the natural logarithm, reflected below zero; the sign-preserving power, with the square root for sqrt; sign(x) * log1p(|x| / c)), and mapped piecewise over the transformed domain, Invert undoes the transform, a number the transform cannot take has no position (null for a data value), a color scale takes its position from the transformed domain, and Fraction gives the position of a value along the transformed domain. Phase 8 adds the Time and Utc kinds (CreateTime): the piecewise linear arithmetic of d3 scaleTime over millisecond instants (domain, range, clamp, round, reverse, Invert to an instant, and Fraction as for a linear scale; a value that is not a valid date has no position), carrying the TimeCalendar for the time ticks and the nice boundaries, kept distinct from the Linear kind so that every site that handles numbers is a deliberate choice. Phase 14 adds the ScaleInvalidOutput record (a number and a text) that WithInvalidOutput attaches to a copy of a model whose HasContinuousDomain is true (Vega-Lite's config.scale.invalid value of a channel): Map and MapText return it as it is, not passed through the scale, for a value that does not read as a number. */

        comment sourceRef /* Source: src/DemaConsulting.CanvasNet.VegaLite/Scales/ScaleModel.cs, src/DemaConsulting.CanvasNet.VegaLite/Scales/NamespaceDoc.cs */
        comment testRef /* Test: test/DemaConsulting.CanvasNet.VegaLite.Tests/Scales/ScaleModelTests.cs and ScaleModelTimeTests.cs (the scale.invalid output is exercised through MarkBuilderScaleInvalidTests.cs) */
        comment designRef /* Design: docs/design/canvas-net-vega-lite/scales/scale-model.md */
        comment verificationRef /* Verification: docs/verification/canvas-net-vega-lite/scales/scale-model.md */
        comment reqRef /* Requirements: docs/reqstream/canvas-net-vega-lite/scales/scale-model.yaml */
    }
}
