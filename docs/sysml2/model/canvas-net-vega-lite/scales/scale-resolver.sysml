package CanvasNet {
    part def ScaleResolver {
        doc /* The internal static ScaleResolver with the ResolvedScales, ResolvedScale, and RangeEnd types: it infers, for each encoding channel of a single view, the scale Vega-Lite would build, as a description that is independent of the size of the data rectangle until ResolvedScale.CreateModel is given it. Rules (ported from Vega-Lite and Vega with attribution): quantitative positions are linear and discrete positions are band scales for rect, bar, image, rule, and tick marks and point scales otherwise;         color, fill, and stroke fields are ordinal (the named range category or ordinal of config.range, the scale's range or scheme) and a quantitative color is a sequential scale (diverging with a middle value) over the ramp, heatmap, or diverging range, a named scheme or a list of colors interpolated in the color space that interpolate names; quantize, quantile, and threshold scales classify (five scheme colors by default, quantileCount and quantizeCount 4 for the spread numbers of a size, thresholds plus one); shape, strokeDash, strokeWidth, fillOpacity, strokeOpacity, and angle have scales for the marks that use them (Vega-Lite's supportMark) with the symbol list, five dash patterns, and default numeric ranges; rangeMin and rangeMax replace the entries of a default range; an unknown scheme name or named range is a VegaLiteSpecException as in Vega; size and opacity use the default ranges of the mark; the linear domain is the extent of the valid values with the zero rule, domainMin, domainMax, and domainMid, an explicit domain (all entries kept, so a domain and range of more than two entries map piecewise; zero, padding, and nice change only the end entries), nice, and pixel padding applied in Vega's order; a band or point scale uses the first two entries of its range; a discrete domain is sorted ascending by default (sort may be ascending, descending, null, an array, an encoding sort such as "-y" or an object with an encoding channel and an order, or an object with any orderable aggregate op - count, valid, missing, distinct, sum, product, mean, average, median, q1, q3, min, max, the variances and deviations, stderr, and the interval ends - an optional field, and an optional order, which orders the categories by that aggregate over the rows of the raw table, stably, a category without a valid number first, via IsSupportedFieldSort and the MeasureCell accumulators of the AggregateTransforms unit); Phase 6 makes the resolver plan driven (the partial files ScaleResolver.Plan.cs and ScaleResolver.Sort.cs): it reads the field that the EncodingPlan names for each channel (the bin start, the aggregate measure, or the end of a stack), builds the domain of a stacked channel from the start and end values (0 to 1 for a normalized stack), of a range channel from the union of a field and its secondary field, of a binned channel from the start of the first and the end of the last bin without zero or nice, of a pre-binned channel from the union of its start and end, and of a scale with the domain "unaggregated" from the extent of the raw field, and gives a discrete bin the labels of its ranges ordered by bin start; paddings follow the mark and the scale configuration; a step-driven discrete scale reports the extent the view needs; InferOrient gives the horizontal or vertical orientation of bar, tick, and rule marks. An invalid scale domain, range, or scheme is a VegaLiteSpecException with the pointer, a discrete domain, a range, or a scheme count beyond MaxScaleDomainSize is a VegaLiteRenderException, the values of a quantile scale are counted against the cell limit and charged to the evaluation-step budget, and cancellation is polled while the data is scanned and sorted. The log, pow, sqrt, and symlog scale types resolve to a continuous scale with a ScaleTransform (base, exponent with sqrt as 0.5, constant with Vega's defaults): a log scale has no zero, is niced to powers of its base, widens its padding in the logarithm, and refuses a domain that includes or crosses zero with a located VegaLiteSpecException (an explicit domain) or VegaLiteRenderException (the data), where Vega only warns. A binned quantitative color, fill, or stroke gets the bin-ordinal scale (the default of Vega-Lite): its domain is the edges of the bins of the encoding, its range one color per bin from the scheme, and a field without a finite value has no edge and no color; the other binned channels keep their scale over the start of the first bin to the stop of the last, and an explicit bin-ordinal type on a field that is not a binned quantitative color is replaced by the default type. A conditional channel resolves its scale from the field definition that the plan names (its own, or the condition that holds a field); conditions that hold only values resolve none. Phase 8 (ScaleResolver.Time.cs) gives a temporal field a scale: a time scale (a UTC scale for a utc time unit) on the position, size, opacity, stroke width, and angle channels, a continuous color scale over milliseconds for the color channels (the discretizing types fall back to it), an ordinal scale for shape and stroke dash, the explicit types time and utc for a temporal field only; the domain is the extent of the dates (a bar or rect of a time unit also reads the end field, a point the start only), with no zero, no nice by default (nice as true, a count, an interval name, or an interval and a step), and no padding for the bars of a time unit; an explicit domain, domainMin, domainMax, and a datum read timestamps, date texts, datetime objects, and the part of a single unit in the calendar of the scale, bounded by MaxScaleDomainSize before any entry is converted; a nominal or ordinal field with a time unit gets a band, point, or ordinal scale over the unit starts in date order. The ResolvedScale carries the Calendar, TimeUnit, IsTemporalField, NiceInterval, and HasBandEnd that the guides and marks read. Phase 9 resolves the polar channels theta and radius for the arc and text marks (ChannelGroup.Polar and ResolvedScale.IsPolar: linear by default, band for an arc and point for a text of a discrete field, the explicit transformed types, the zero rule of the configuration, no nice and no padding, the range 0 to 2 pi for theta and 0 to half of the smaller side of the view for radius, with theta2 and radius2 reading the scale of their main channel), gives a channel a scale only for the marks that draw it (ChannelIsDrawn, the support table of theta, radius, size, strokeDash, angle, shape, and text), and infers the orientation of the area (y2 or x2, a binned secondary position reversing it), of the line, tick, and area against a temporal axis, and of the trail and arc (vertical). Phase 10 (ScaleResolver.Layers.cs, ResolveLayers with LayerScaleInput and LayeredScales; ResolvedScale is a record with HasExplicitDomain and DomainOrder) resolves the scales of the layers of a layered view: each layer is resolved as a view, then the scales of a channel that several layers carry and that resolve leaves shared are merged (the owner is the scale of the highest precedence, band before point before the rest; the continuous domain is the union of the domains of the layers after each layer's own zero rule, or the extent of the union of the explicit domains (equal explicit domains count once, a piecewise one is kept, implicit domains are ignored next to them); the discrete domain is the ordered union of the categories, failing closed beyond MaxScaleDomainSize; the owner is resolved again over the combined domain; each layer receives the shared scale bound to its own field, so the marks of all layers line up; the titles join as a, b), an independent channel keeps one scale for each layer or group, scales that cannot be combined keep their own and are reported with vl-layer-scale-conflict, a view with one layer gives exactly the single-view result. Phase 11 resolves the scales across the views of a composition by the same grouping with the defaults of their kind (the children of a concatenation keep the x, y, xOffset, yOffset, theta, and radius scales independent and share the others, the cells of a facet share everything but theta, resolve deciding otherwise; vl-layer-scale-conflict names the view) and LayeredScales.HintsFor gives the step size (the natural extent) of the discrete x and y scale that all the layers of one chart use. The xOffset and yOffset channels (ScaleResolver.Offsets.cs: OffsetDecision with Supported, TimeUnitParent, NoDiscreteParent, Ranged, and UnsupportedContinuous, DecideOffset, HasNestedOffset for the discrete parents (a ranged offset included), HasRangedOffset, HasTimeUnitOffset, StepForOf, and ApplyNestedOffsets, which runs once for each scale map so that layers merge an offset domain once) are resolved as Vega-Lite 6.5 nests them: an offset has a scale only when its position channel is a nominal or ordinal field, with or without a time unit (an ordinary band parent), or a temporal field with a supported time unit (it parses, is not binned or maxbins, its smallest part is not the day of the week, and the mark is not a rect; the TimeUnitParent) and, for a bar or an area, when the offset field is not continuous (a continuous offset of a bar or an area is Ranged when it is Vega-Lite's ranged offset of Phase 14, an unbinned quantitative offset of a nominal or ordinal position without x2 or y2, which is drawn as a range from the zero of its linear offset scale, the one offset scale whose zero rule is true; otherwise it is UnsupportedContinuous, the offset is ignored and the FeatureCatalog reports vl-offset-ranged, and vl-offset-position is reported for a position that cannot hold an offset); the position that holds a nested discrete offset is always a band scale (also for the marks that have a point scale and for an explicit point type), while the position of a time unit parent stays a time scale and its offset scale gets the range that the marks compute (ResolvedScale.CreateModel with a nested range in pixels instead of the default range, rangeMin, rangeMax, a given range, and reverse still applying) with paddingInner and paddingOuter from config.scale.bandWithNestedOffsetPaddingInner and bandWithNestedOffsetPaddingOuter (0.2 each) unless the scale gives a padding or explicit paddings; the offset scale is a band scale for bar, rect, image, rule, and tick marks and a point scale (outer padding 0.5) for the others, with the whole field as its domain in the channel sort and its paddings from config.scale.offsetBandPaddingInner and offsetBandPaddingOuter (0 by default), or a linear or time scale without zero (a ranged offset has zero), nice, or pixel padding for a quantitative or temporal offset, and spans the bandwidth of the band of the position; with a step size the step of the position is the step times the band space of the offset categories (their count and offset paddings) divided by one minus the inner padding of the position when the step is for the offset (the default for a discrete offset, the width or height step object accepting for: position or offset), and for: position keeps the step on the position scale. Phase 12 (milestone 1, ScaleResolver.Raw.cs) takes the domain of a scale as it is from its domainRaw or from the variable parameter named by a scale domain of the form param (the parameter values of the call are an optional argument of Resolve and ResolveLayers): at least two numbers or dates for a continuous scale (a piecewise domain for more) and at least one scalar for a band, point, or ordinal scale, without the zero rule, domainMin, domainMax, domainMid, pixel padding, or nice (HasRawDomain), keeping the own domain of a discretizing scale, of a parameter without a value, and of a selection parameter, delivering the warning vl-scale-domain-raw for a value that no scale can use, and marking a scale whose domain is a parameter reference so that its marks are clipped (ClipMarks); layers that share a scale take the raw domain of a member as the shared domain. Phase 12 (milestone 2b) also takes the extent of a scale from a selection or a bin (ScaleResolver.Raw.cs: FindExtent, BinExtentOf, and HasSelectionExtent; the selections and the node of the view are optional arguments of Resolve and ResolveLayers): the range that an interval selection bound to the scales (resolve global, a continuous scale of a channel it projects) holds for the unit that is the whole view or a layer of the top-level layers, else the selected range of the field that a scale domain of the form param names on a selection (the field, else the encoding, else the first projected field, with vl-param-selection-projection), else the extent that the bin of the encoding names (the domain of the scale and the span of the step); the precedence is the binding, then the domain, then the bin extent, a selection that holds nothing keeps the domain of the data, and the marks are clipped whenever the scale has any of these extents. */
                comment sourceRef /* Source: src/DemaConsulting.CanvasNet.VegaLite/Scales/ScaleResolver.cs, src/DemaConsulting.CanvasNet.VegaLite/Scales/ScaleResolver.Plan.cs, src/DemaConsulting.CanvasNet.VegaLite/Scales/ScaleResolver.Sort.cs, src/DemaConsulting.CanvasNet.VegaLite/Scales/ScaleResolver.Color.cs, src/DemaConsulting.CanvasNet.VegaLite/Scales/ScaleResolver.Range.cs, src/DemaConsulting.CanvasNet.VegaLite/Scales/ScaleResolver.Time.cs, src/DemaConsulting.CanvasNet.VegaLite/Scales/ScaleResolver.Layers.cs, src/DemaConsulting.CanvasNet.VegaLite/Scales/ScaleResolver.Offsets.cs, src/DemaConsulting.CanvasNet.VegaLite/Scales/ScaleResolver.Raw.cs */
                comment testRef /* Test: test/DemaConsulting.CanvasNet.VegaLite.Tests/Scales/ScaleResolverTests.cs, test/DemaConsulting.CanvasNet.VegaLite.Tests/Scales/ScaleResolverPlanTests.cs, test/DemaConsulting.CanvasNet.VegaLite.Tests/Scales/ScaleResolverColorTests.cs, test/DemaConsulting.CanvasNet.VegaLite.Tests/Scales/ScaleResolverBinTests.cs, test/DemaConsulting.CanvasNet.VegaLite.Tests/Scales/ScaleResolverTimeTests.cs, test/DemaConsulting.CanvasNet.VegaLite.Tests/Scales/ScaleResolverPolarTests.cs, test/DemaConsulting.CanvasNet.VegaLite.Tests/Scales/ScaleResolverLayerTests.cs, test/DemaConsulting.CanvasNet.VegaLite.Tests/Scales/ScaleResolverCompositionTests.cs, test/DemaConsulting.CanvasNet.VegaLite.Tests/Scales/ScaleResolverOffsetTests.cs, test/DemaConsulting.CanvasNet.VegaLite.Tests/Scales/ScaleResolverDomainRawTests.cs, test/DemaConsulting.CanvasNet.VegaLite.Tests/VegaLiteSelectionExtentIntegrationTests.cs, test/DemaConsulting.CanvasNet.VegaLite.Tests/Scales/MarkChannelGatingTests.cs, test/DemaConsulting.CanvasNet.VegaLite.Tests/Transforms/RowTransformsTests.cs (the sort-by-field tests) */
        comment designRef /* Design: docs/design/canvas-net-vega-lite/scales/scale-resolver.md */
        comment verificationRef /* Verification: docs/verification/canvas-net-vega-lite/scales/scale-resolver.md */
        comment reqRef /* Requirements: docs/reqstream/canvas-net-vega-lite/scales/scale-resolver.yaml */
    }
}
