package CanvasNet {
    part def SpecNormalizer {
        doc /* The internal static partial SpecNormalizer with the LayerTree, LayerNode, LayerResolve, ResolveMode, ViewKind, CompositionSettings, CompositionAlign, FacetDefinition, RepeaterValues, ExpandedLayers, CompositeAxis, and CompositeBuilder types: it reduces the views of a parsed specification to the tree of views whose leaves are the unit views that are drawn, so that every later stage draws unit views and needs no special case for layers, compositions, or composite marks. Layers(tree, limits, config) builds the LayerTree with an explicit stack: a specification without composition is one unit view, the root itself, so a single view takes the path it always took; the objects of a layer array are the layers of a layered view (unit views or layered views, to any depth); a concat, hconcat, or vconcat is a Concat node whose children are its charts; a facet with a spec, and a unit view with a row, column, or facet encoding channel (the root or a child of a concatenation, not a unit view in a layer or in the spec of a facet), is a Facet node over one chart, the synthetic body of a faceted unit view having its mark, size, and encoding without the faceting channels; a repeat is expanded without reading data into a Concat node (an array, or the row-major product of rows and columns) or a Layer node (layers) of copies of its spec, each copy knowing the values it repeats, whose {"repeat": ...} field references are replaced by those values (a reference with no value dropping its channel with a warning), the number of copies being checked against MaxViews before any copy is made. Each node of a composition has the layout settings that Vega-Lite's extractCompositionLayout reads (columns, spacing, align, center, bounds, over the configuration) and the resolve defaults of its kind (the position, theta, and radius scales of the children of a concatenation independent and their axes never shared, the scales of a facet shared except theta). A layer inherits as in Vega-Lite: the encoding of the layered views above it in its chart (the outermost first, a channel of an inner view replacing the outer channel in place and a new channel added after the existing ones, as a node that is not adopted by its parent so every pointer, line, and column stays that of the specification), the width and height of its chart, and, as the view's own, the data and the transform that the document applies down the tree (the transform of a layered view first); the resolve of each view that holds views is read into a LayerResolve. MaxViews (every view, the views of an expansion and the copies of a repeat included) and MaxCompositionDepth (the nesting of layers, concatenations, facets, and repeats) fail closed with a located VegaLiteRenderException at the exact limit. Expand(tree, config, limits) replaces a unit view whose mark is boxplot, errorbar, or errorband by a layered view of the primitive layers that Vega-Lite normalizes it to, written as synthetic nodes located at the mark, with the expressions it writes compiled into a derived specification tree: a boxplot as the outlier points, the whiskers (rules and optional end ticks over the values inside the fences, or from the minimum to the maximum for min-max), and the box with its median tick, with the defaults of config.boxplot; an errorbar from raw observations (the stderr, stdev, ci, or iqr extent around the mean or median), a pre-aggregated range, or errors, as a rule with optional ticks; an errorband as a rect (one dimension) or an area (two dimensions) with optional rule or line borders; the part switches, part properties, orientation, grouping channels, and titles follow Vega-Lite, and an orientation or encoding that cannot be decided is a VegaLiteSpecException at the mark. The unit performs no file or network access and holds no state; the expansion, composition, and repeat rules are ported from Vega-Lite compositemark, normalize, and spec with attribution (the files carry the provenance header). The data-dependent part of the tree (phase 11): LayerTree.InstantiateFacet replaces the template of a facet by one copy for each cell the data gives (the same view and unit objects, the cell on every node, their own chart roots) and refreshes the units, compositions, and view count (Refresh), FacetViews counts the views of a cell and the views outside the cells so that MaxViews is checked before the cells are made, and DataSites groups the views by the data object they declare so that a table is loaded once for the copies of a repeat and the cells of a facet, with the views and facets whose fields the loader parses as dates. Phase 13: a non-binned timeUnit with parts on a channel that groups the rows of a boxplot, errorbar, or errorband becomes a timeUnit transform plus a derived field, prepended to the transforms of the top-level view, with the default title of a time unit and the format type time for a channel that is not temporal; Phase 14 (Vega-Lite's extractTransformsFromEncoding, CompositeGrouping): a bin of a grouping channel becomes a bin transform before the aggregate (the channel then reads the start as binned data with the end as x2 or y2 and the default title), a time unit (maxbins form included) a timeUnit transform, and an aggregate a measure that is added to every aggregate of the expansion and read by the channel (an errorbar adds an aggregate grouped by the channels when a channel aggregates); a bin that is binned or false and a binned time unit leave the field as it is. */

        comment sourceRef /* Source: src/DemaConsulting.CanvasNet.VegaLite/SpecModel/SpecNormalizer.cs, src/DemaConsulting.CanvasNet.VegaLite/SpecModel/SpecNormalizer.Composition.cs, src/DemaConsulting.CanvasNet.VegaLite/SpecModel/SpecNormalizer.Repeat.cs, src/DemaConsulting.CanvasNet.VegaLite/SpecModel/SpecNormalizer.Composite.cs, src/DemaConsulting.CanvasNet.VegaLite/SpecModel/SpecNormalizer.BoxPlot.cs, src/DemaConsulting.CanvasNet.VegaLite/SpecModel/SpecNormalizer.ErrorBar.cs, src/DemaConsulting.CanvasNet.VegaLite/SpecModel/SpecNormalizer.PathOverlay.cs */
        comment testRef /* Test: test/DemaConsulting.CanvasNet.VegaLite.Tests/SpecModel/SpecNormalizerTests.cs, test/DemaConsulting.CanvasNet.VegaLite.Tests/SpecModel/SpecNormalizerCompositionTests.cs, test/DemaConsulting.CanvasNet.VegaLite.Tests/SpecModel/SpecNormalizerRepeatTests.cs, test/DemaConsulting.CanvasNet.VegaLite.Tests/SpecModel/SpecNormalizerFacetCellTests.cs, test/DemaConsulting.CanvasNet.VegaLite.Tests/SpecModel/SpecNormalizerBoxPlotTests.cs, test/DemaConsulting.CanvasNet.VegaLite.Tests/SpecModel/SpecNormalizerErrorBarTests.cs */
        comment designRef /* Design: docs/design/canvas-net-vega-lite/spec-model/spec-normalizer.md */
        comment verificationRef /* Verification: docs/verification/canvas-net-vega-lite/spec-model/spec-normalizer.md */
        comment reqRef /* Requirements: docs/reqstream/canvas-net-vega-lite/spec-model/spec-normalizer.yaml */
    }
}
