package CanvasNet {
    part def ExpressionReferenceFolder {
        doc /* The internal static ExpressionReferenceFolder with the FoldResult record, and the internal static ExpressionReferenceSites: Vega-Lite compiles an ExprRef (an {"expr": ...} object where the schema allows a value) to a Vega signal, so in a static render its value is the expression evaluated once with the parameters at their initial state. The SpecParser compiles every reference at a static site when the document is opened (a site that Vega-Lite's schema allows one at and that no row reads: the title, the padding and background of the top-level view, the mark properties that are not row-bound including the overlays and the parts of a composite mark, the properties of an axis, a legend, a header, a scale, and the view background, the value and datum of a channel definition, and the same properties in the configuration of the top-level view) and lists them as StaticReference records; ExpressionReferenceSites holds the schema-derived table of the owners and properties and the explicit-stack walk that finds the references without entering the data, datasets, transforms, parameters, or projection. At render time, after the parameters are evaluated, Fold evaluates each listed reference once with the evaluator of the call (every evaluation is charged to the step budget) and rewrites the tree by copying only the path from the root to each reference (SpecNode.Overlay and SpecNode.Synthetic), so untouched subtrees keep their node identity and the values are located at the reference they replace; the configuration resolver, the normalizer, the scales, the guides, the marks, the title, and the layout then read values. A reference that reads datum stays in place and the feature catalog reports it; a number that is not finite folds to null; a date folds to its milliseconds only in a scale domain, elsewhere (and for a regular expression) the reference stays and a vl-expr-ref warning is returned; the text of a title or a mark takes the JavaScript text of a number or a boolean; a text longer than the string limit and an exceeded step budget are located VegaLiteRenderExceptions. The sites that the marks evaluate for every row (the paint properties of a mark and the value of a paint channel or a condition) keep their reference. Phase 13 adds the warning vl-param-extent-static, located at a folded reference that reads the parameter of an extent transform (a parameter that the data stage computes after the fold, so it is null at a static site). */

        comment sourceRef /* Source: src/DemaConsulting.CanvasNet.VegaLite/SpecModel/ExpressionReferenceFolder.cs, src/DemaConsulting.CanvasNet.VegaLite/SpecModel/ExpressionReferenceSites.cs */
        comment testRef /* Test: test/DemaConsulting.CanvasNet.VegaLite.Tests/SpecModel/ExpressionReferenceFolderTests.cs */
        comment designRef /* Design: docs/design/canvas-net-vega-lite/spec-model/expression-reference-folder.md */
        comment verificationRef /* Verification: docs/verification/canvas-net-vega-lite/spec-model/expression-reference-folder.md */
        comment reqRef /* Requirements: docs/reqstream/canvas-net-vega-lite/spec-model/expression-reference-folder.yaml */
    }
}
