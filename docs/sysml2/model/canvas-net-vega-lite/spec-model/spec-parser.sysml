package CanvasNet {
    part def SpecParser {
        doc /* The internal SpecParser (a sealed partial class with static Parse entry points over text or UTF-8 bytes), the immutable tree types (SpecNode, SpecNodeKind, NodePosition, SpecTree), and the SpecMetadata record: a single-pass Utf8JsonReader-based reader with an explicit frame stack that builds the SpecNode tree with lazily computed RFC 6901 pointers and one-based UTF-16 line and column positions for every value and property key, decodes strictly (invalid UTF-8 in bytes and an unpaired surrogate in text are a located VegaLiteSpecException, never U+FFFD), enforces MaxSourceLength (InvalidDataException), MaxJsonDepth, and MaxStringLength (VegaLiteSpecException), applies the duplicate-key policy (last value wins at the position of the first, one vl-duplicate-key warning), and validates the shape of the known properties of views, titles, padding, autosize, mark definitions, channel definitions, data formats (a single-character delimiter, the parse property and its entries, a sequence field name), scales, and axes with rule tables and generous sets of known property names taken from the Vega-Lite 6 JSON schema (a wrong type or value is a VegaLiteSpecException with the pointer of the value; an unknown key is a vl-unknown-property warning); it rejects a schema naming plain Vega, never walks inline data rows, and visits nested views with an explicit work stack. Phase 5 adds, in the partial file SpecParser.Transforms.cs and the SpecExpressions type, the compilation (with the ExpressionParser unit) of every expression text the renderer evaluates (the expression of a calculate transform, a text filter, and the expr references of a mark property or channel value of the drawn view), whose syntax, length, and depth errors and references to an undeclared parameter are a VegaLiteSpecException located at the expression string with the expression offset in the message; the validation of the variable parameters of every view (a repeated or reserved name, a value or expr of the wrong form, and a dependency cycle located at the expression of the lowest declared parameter on the cycle) with the ParameterGraph that orders the parameters dependencies first; and the shape validation of the supported transforms (calculate, filter and its predicates, fold, flatten, sample, pivot, and lookup) of every view. Phase 6 adds the partial file SpecParser.Aggregates.cs, which validates the shape of the aggregate, joinaggregate, window, bin, stack, and impute transforms (operation names, required fields, parameters such as ntile and nth_value, frames, bin parameters, sort fields, and key sequences) and of the aggregate, bin, stack, sort, and order properties of the channel definitions with located errors, and offers the sort-form helpers (IsSupportedSort, the sort shorthand, and the channel a sort refers to) to the other units. A sort array item that is an object or an array (other than a date-time object on a temporal field) is a located error, an array that mixes kinds of values is the warning vl-encoding-sort-mixed-types, and an unknown key of a sort object is a vl-unknown-property warning. Phase 7 adds, in SpecParser.Validation.cs, the validation of the structured options of a scale: the domainMid, domainMin, domainMax, rangeMin, and rangeMax numbers, an interpolate (one of the eight color-space names or an object with that type and a numeric gamma), a scheme (a name or an object with a string name, a positive whole count, and an extent of two numbers), and the bins, with a located error at the offending value and a vl-unknown-property warning for an unknown key of a scheme or interpolate object. SpecMetadata reads the schema URL and major version, the title text, the marks, the data references, and the parameter names from a tree. The condition of a channel definition is validated (an object or an array of objects with a test or a param, located errors) and the test of a condition on a drawn channel is compiled once, a predicate object as the expression that PredicateSource writes for it;         ChannelDefinitions finds the field definition of a conditional channel. Phase 8 adds the partial file SpecParser.Time.cs: the validation of a timeUnit wherever it is written (a name of the documented time units with the utc and binned prefixes, or an object with unit or maxbins, step, utc, and binned; an unknown member is a vl-unknown-property warning), of the datetime objects of a scale domain, domainMin and domainMax, the values of an axis and a legend, the values of a predicate, a sort array of a temporal field, and a datum (each a located error at the wrong member), of the interval of a tickCount or a nice property (one of the eight interval names or an object with an interval and a positive step), of the numeric timeUnitBandPosition and timeUnitBandSize of a mark, of the timeUnit transform (classified as supported), and of the date and utc entries of a parse property (a quoted format is required); PredicateSource writes a time predicate as the expression of Vega-Lite (the datetime of the unit parts of the field against the datetime of the value, the utc functions for a utc unit, the week and dayofyear parts omitted with a warning, a range as two comparisons, oneOf as an index test) and the parser compiles it once under the predicate. Phase 9 validates the properties of the line, area, trail, text, and arc marks (interpolate, tension, point, line, invalid, order, strokeDashOffset, strokeMiterLimit, padAngle, innerRadius, outerRadius, radius, radius2, theta, theta2, text, fontStyle, fontWeight, limit, ellipsis, lineBreak, and lineHeight, and the overlay objects of point and line with the mark rules and a warning for an unknown key), the impute object of a position definition (keyvals bounded by MaxScaleDomainSize, method, value, and frame), and compiles the expression and the conditions of a size value for the line, trail, and text marks (the text that is written from a predicate object of a condition or a time-aware filter is compiled with ParseGenerated: it is bound by MaxScaleDomainSize values for a oneOf list and eight times MaxSourceLength, not by MaxExpressionLength; the characters are counted as the text is written, so a text over the budget is refused before it is allocated, and an expr that the user writes as an operand of a predicate is validated as a user expression and bound by MaxExpressionLength at the expr text). Phase 10 (SpecParser.Layers.cs) validates the resolve of a view (scale, axis, and legend objects, the channels that Vega-Lite resolves for each kind, and the values shared and independent) and the extent, center, and part properties of the composite marks boxplot, errorbar, and errorband, and the composition properties (a facet and a repeat need a spec; the shapes of facet, repeat, columns, spacing, align, center, and header; the repeat references; no composition in a layer or in the spec of a facet). Phase 11 compiles the expressions of every view, those of a concatenation, facet, or repeat included. SpecParser.LabelExpressions.cs compiles, when the document is opened, the labelExpr of every axis, legend, and facet header and of config.axis, the other axis configuration, and config.header, headerRow, headerColumn, and headerFacet (not config.legend, which Vega-Lite does not read), so that a syntax error or an unknown parameter is a VegaLiteSpecException at the text; the width and height step objects accept for: position or offset (any other value is a VegaLiteSpecException at the property). Phase 12 (milestone 1) also compiles, at the end of the parse, every expression reference at a static site that Vega-Lite's schema allows (the title, the padding and background of the top-level view, the mark properties that no row reads, the properties of the guides, scales, and view background, the value and datum of the channels, and the same properties in the configuration of the top-level view; a syntax error or an undeclared parameter is a VegaLiteSpecException) and lists them as StaticReference records in SpecExpressions.StaticReferences for the ExpressionReferenceFolder; the gridAlign of a legend accepts an expression reference. Phase 13 adds the partial file SpecParser.Statistics.cs, which validates the shape of the regression, loess, density, quantile, and extent transforms (the method, an integer order from 0 to 64, a bandwidth, the steps, the resolve, the probabilities, the extent pair, the group fields, and the output names) and the pivot op (an aggregate operation), applies the isExtent rule of Vega-Lite (an extent next to a regression or a density is their option and not a transform), makes the parameter of an extent transform visible to the expressions of its view and of the views below it (IsExtentParameter and ExtentParameterNames), and rejects an extent parameter that repeats a declared parameter. */
                comment selectionRef /* Phase 12 (milestone 2): the parser validates a selection parameter (select point or interval as a text or an object, fields and encodings as arrays of texts, resolve, views) and the legacy selection property (single, multi, interval), accepts every interaction property unchecked, finds a selection by name from every view of the specification (SelectionDeclarations: the declarations of a view, the assignment of selections to unit views as Vega-Lite's top-level selection normalizer does, and the names of unnamed units), and compiles a condition or predicate on a selection as the text that Vega-Lite compiles for it, under the same generated-expression budget as every predicate that is written as an expression (ExpressionParser.ParseGenerated; the characters are counted as the text is written and a text over the budget is refused before it is allocated) (PredicateSource: !length(data("name_store")) || vlSelectionTest("name_store", datum), length(...) && ... for empty false, vlSelectionIdTest for a point selection over the identity of the rows, the resolve as a third argument); a condition on a param or a legacy selection is a condition on a predicate (ChannelDefinitions.TestConditions) and its field gives the scale and legend of the channel. */
                comment sourceRef /* Source: src/DemaConsulting.CanvasNet.VegaLite/SpecModel/SelectionDeclarations.cs, src/DemaConsulting.CanvasNet.VegaLite/SpecModel/SelectionDeclarations.Assignment.cs, src/DemaConsulting.CanvasNet.VegaLite/SpecModel/SpecParser.cs, src/DemaConsulting.CanvasNet.VegaLite/SpecModel/SpecParser.Validation.cs, src/DemaConsulting.CanvasNet.VegaLite/SpecModel/SpecParser.Transforms.cs, src/DemaConsulting.CanvasNet.VegaLite/SpecModel/SpecParser.Aggregates.cs, src/DemaConsulting.CanvasNet.VegaLite/SpecModel/SpecParser.Time.cs, src/DemaConsulting.CanvasNet.VegaLite/SpecModel/SpecParser.Layers.cs, src/DemaConsulting.CanvasNet.VegaLite/SpecModel/SpecParser.LabelExpressions.cs, src/DemaConsulting.CanvasNet.VegaLite/SpecModel/SpecExpressions.cs, src/DemaConsulting.CanvasNet.VegaLite/SpecModel/SpecNode.cs, src/DemaConsulting.CanvasNet.VegaLite/SpecModel/SpecMetadata.cs, src/DemaConsulting.CanvasNet.VegaLite/SpecModel/ChannelDefinitions.cs, src/DemaConsulting.CanvasNet.VegaLite/SpecModel/PredicateSource.cs, src/DemaConsulting.CanvasNet.VegaLite/SpecModel/NamespaceDoc.cs */
                comment testRef /* Test: test/DemaConsulting.CanvasNet.VegaLite.Tests/SpecModel/SpecParserSelectionTests.cs, test/DemaConsulting.CanvasNet.VegaLite.Tests/SpecModel/SpecParserTests.cs, test/DemaConsulting.CanvasNet.VegaLite.Tests/SpecModel/SpecParserAggregatesTests.cs, test/DemaConsulting.CanvasNet.VegaLite.Tests/SpecModel/SpecParserConditionTests.cs, test/DemaConsulting.CanvasNet.VegaLite.Tests/SpecModel/SpecParserTimeTests.cs, test/DemaConsulting.CanvasNet.VegaLite.Tests/SpecModel/SpecParserMarkTests.cs, test/DemaConsulting.CanvasNet.VegaLite.Tests/SpecModel/SpecParserImputeTests.cs, test/DemaConsulting.CanvasNet.VegaLite.Tests/SpecModel/SpecParserResolveTests.cs, test/DemaConsulting.CanvasNet.VegaLite.Tests/SpecModel/SpecParserCompositionTests.cs, test/DemaConsulting.CanvasNet.VegaLite.Tests/SpecModel/FeatureCatalogLabelExprAndOffsetTests.cs, test/DemaConsulting.CanvasNet.VegaLite.Tests/SpecModel/PredicateSourceTests.cs, test/DemaConsulting.CanvasNet.VegaLite.Tests/SpecModel/PredicateSourceTimeTests.cs, test/DemaConsulting.CanvasNet.VegaLite.Tests/SpecModel/ChannelDefinitionsTests.cs */
        comment designRef /* Design: docs/design/canvas-net-vega-lite/spec-model/spec-parser.md */
        comment verificationRef /* Verification: docs/verification/canvas-net-vega-lite/spec-model/spec-parser.md */
        comment reqRef /* Requirements: docs/reqstream/canvas-net-vega-lite/spec-model/spec-parser.yaml */
    }
}
