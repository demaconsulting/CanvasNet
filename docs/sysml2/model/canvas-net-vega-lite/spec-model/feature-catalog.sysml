package CanvasNet {
    part def FeatureCatalog {
        doc /* The internal static FeatureCatalog with the FeatureReport record and the FeatureReportKind enumeration: a pure function of the parsed SpecTree that lists every construct of a Vega-Lite specification that the renderer recognizes but does not implement, each with a stable lower-case vl- identifier (vl-schema-version, vl-data-*, vl-mark-type, vl-channel-name, vl-type-*, vl-scale-*, vl-encoding-*, vl-guide-*, vl-format-type-custom, vl-expr-*, vl-transform-name, vl-composition-*, vl-param-*, vl-projection, vl-layout-fit-step) and the exact location, sorted by line and column with a stable sort. Phase 11 retires vl-layout-autosize-fit, vl-layout-autosize-fit-x, and vl-layout-autosize-fit-y (fit, fit-x, and fit-y are drawn, so no autosize type is reported; the identifiers are never reused) and adds the warning vl-layout-fit-step, which the renderer's layout produces (a fit dropped for a step size) and the catalog itself does not; a fit or a container size of a composition is the warning vl-composition-property-ignored. Phase 5 removes the reports of the supported expressions and transforms (vl-expr-calculate, vl-expr-filter, and vl-transform-calculate, filter, fold, flatten, sample, pivot, and lookup of the drawn view, vl-param-variable of the drawn view, and vl-expr-ref at the row-bound sites) and adds vl-expr-function-name (a function outside the whitelist, the name lower-cased in the identifier and as written in the message), vl-expr-view-state (signal, event, item, and undeclared width, height, padding, autosize, background, or cursor), vl-expr-construct-name (bitwise and shift operators and in), each at the expression string with the offset in the message, plus vl-transform-filter-param, vl-transform-filter-timeunit, vl-transform-filter-datetime, vl-transform-pivot-op, and vl-transform-lookup-param for the parts of supported transforms that are not executed; Phase 6 removes the reports of the supported grouping transforms and encodings (vl-transform-aggregate, joinaggregate, window, bin, stack, and impute of the drawn view, vl-encoding-aggregate, vl-encoding-stack, vl-encoding-bin of x and y, vl-scale-bin-ordinal, vl-encoding-sort of the supported forms, vl-channel-x2 and vl-channel-y2 of bar, rect, and rule marks, and vl-channel-order when it orders an active stack, decided with the StackRules of the Transforms subsystem) and adds vl-encoding-bin-extent-param and vl-transform-bin-extent-param (an extent given by a parameter, ignored) and vl-encoding-stack-nonlinear (an explicit stack on a scale that is not linear); the transforms regression, loess, density, quantile, and extent, every transform (the timeUnit transform included) and variable parameter of a nested view, the encoding impute (vl-encoding-impute), selection parameters, conditional encodings (vl-encoding-condition), bin: "binned" on a channel other than x and y and a bin of order or a secondary channel (vl-encoding-bin), and the channel sorts that are not ascending, descending, null, a value list, an encoding sort, or an aggregate object (vl-encoding-sort) stay reported. The Step 0 sort diagnostics refine the channel sorts: a sort that refers to a channel the encoding lacks is vl-encoding-sort with a message that names the channel, and a sort array, channel, or object on a quantitative field with a continuous scale is the warning vl-encoding-sort-ignored. Phase 7 (colors and channels) removes vl-scale-color-ramp (retired: continuous colors are drawn), the reports of the scale types sequential, quantile, quantize, and threshold and of the scale properties domainMid, domainMin, domainMax, rangeMin, rangeMax, and interpolate, the report of an unavailable scheme (an unknown scheme is a specification error), and vl-channel-shape, vl-channel-strokewidth, vl-channel-strokedash, vl-channel-fillopacity, vl-channel-strokeopacity, and vl-channel-angle for the marks that draw them (shape, angle, and strokeDash stay reported and ignored on a mark that does not draw them), and adds vl-scale-interpolate-cubehelix, vl-shape-path (a custom SVG path shape, drawn as a circle), and the warning vl-scale-type-ignored (a scale type that the channel or field type cannot use, and a quantitative field on shape or strokeDash). The log-family scales remove the reports of the scale types log, pow, sqrt, and symlog and of the scale properties base, exponent, and constant (vl-encoding-stack-nonlinear stays for an explicit stack on a scale that is not linear, and its message says that the marks of a log, pow, sqrt, or symlog scale are not stacked). It is the single definition of the supported boundary: supported marks, channels, scale types, scale properties, and data sources are absent from its result. It classifies a data url as remote with IsRemoteDataUrl (a scheme of two or more characters other than file, a file: URI with a host, localhost included, or a malformed one, or a path that starts with two slashes or backslashes: vl-data-remote-url, never fetched; a local path - relative, absolute, a drive path such as C:\x, C:/x, or C:x, or a file: URI without a host, whose local path LocalPathOfFileUri returns - is supported and not reported), does not report a custom parse date format (it is applied by the data stage) and reports text or object datasets as vl-data-values-text or vl-data-geo, chooses a data source by precedence rather than key order, and reports an empty or sourceless data object as the warning vl-data-empty; it opens no file, reads no data rows, and uses no network. The identifiers vl-data-file, vl-data-named, vl-data-sequence, vl-data-parse, vl-data-format-*, and vl-data-property are retired (their constructs are supported). The warnings vl-duplicate-key, vl-unknown-property, and vl-encoding-sort-mixed-types are produced by the SpecParser unit. A condition on a channel that takes none is vl-encoding-condition; a condition on a parameter, or a test that names a selection or a parameter that is not a variable,         is vl-encoding-condition-param; the conditions with a test on the other drawn channels are applied and are not reported (a time unit or a date object in a test is evaluated since Phase 8). Phase 8 (time) removes the reports of the temporal type (vl-type-temporal), the time unit of an encoding (vl-encoding-timeunit), the timeUnit transform of the drawn view (vl-transform-timeunit), the time and utc scale types (vl-scale-time and vl-scale-utc), a time unit or a date object in a filter predicate or a condition test (vl-transform-filter-timeunit, vl-transform-filter-datetime, and vl-encoding-condition-test), and a custom parse date format (vl-data-parse-date-format), narrows vl-encoding-bandposition to a band position on a field without a time unit, narrows vl-format-type-custom to the format types other than number, time, and utc, and adds vl-timeunit-binned (a binned time unit, ignored), vl-timeunit-maxbins (the maxbins form in a predicate), vl-encoding-bandposition-rect (a band position or time unit band position other than one half on a bar or rect with a time unit, drawn at one half), vl-encoding-datum-datetime (a datetime object as a datum, the channel ignored), and the warnings vl-predicate-timeunit-part (a week or day-of-year part of a predicate unit, not applied as in Vega-Lite), vl-scale-nice-interval and vl-guide-axis-tickcount-interval (an interval on a scale that is not a time scale), vl-scale-zero-ignored (a zero property of a time scale), and an extended vl-scale-type-ignored (a scale type that a temporal field cannot use). Phase 9 draws the marks line, area, trail, text, and arc (they are no longer reported, in the same commit as MarkBuilder.IsSupported), accepts the order and detail channels on every mark, the x2 and y2 of an area, and the channels text, theta, radius, theta2, and radius2 (each reported as vl-channel-name, not drawn by the mark, on a mark that ignores it, by ScaleResolver.ChannelIsDrawn, which also gates size, strokeDash, angle, and shape), no longer reports the impute of x and y (vl-encoding-impute remains for any other channel), and adds vl-mark-invalid-show (show and null at the value), the warning vl-mark-invalid-domains (filter and break-paths-filter-domains), vl-mark-interpolate-bundle-area (an area with bundle, drawn linear), vl-mark-interpolate-unknown (an interpolate name of a line or area that Vega-Lite does not know, drawn linear), each of the three also for a value that the mark gets from the configuration of the specification (reported at the configuration, once), vl-encoding-stack-impute-bin (a stacked path mark with a binned dimension), and vl-format-type-custom for a custom format type of a text channel; geoshape and image stay vl-mark-geoshape and vl-mark-image. Phase 10 retires vl-composition-layer, vl-mark-boxplot, vl-mark-errorbar, and vl-mark-errorband (the layer composition and the composite marks are drawn), words the vl-transform report of a view inside a concat, hconcat, vconcat, facet, or repeat as not applied and names the composition, visits the merged encoding of each layer with that layer's mark (a finding reported once), and adds vl-layer-property-ignored (a width, height, autosize, padding, background, config, datasets, or title in a layer), vl-composite-grouping (a bin, a time unit, or an aggregate on a channel that groups the rows of a composite mark), and vl-channel-xerror, vl-channel-xerror2, vl-channel-yerror, and vl-channel-yerror2 for a mark that does not use the error channels. Phase 11 retires vl-composition-concat, vl-composition-hconcat, vl-composition-vconcat, vl-composition-repeat, and vl-composition-facet (a concatenation, a repeat, and a facet are drawn), no longer words the vl-transform report as not applied because of a composition (every view of every composition has its transforms applied), visits the merged encoding of every unit of a concatenation, a facet, or a repeat, narrows vl-channel-row, vl-channel-column, and vl-channel-facet to a unit view that cannot be faceted (a layer, or the spec of a facet), and adds the warning vl-composition-property-ignored (a width, height, or autosize other than pad of a composition, a container size of a view inside one, and a padding, background, config, datasets, or autosize of a view inside one) and the reports vl-facet-field-transform (a bin, time unit, or aggregate of a facet field, not applied), vl-facet-sort (a sort by a field and an operation, ascending order used), and vl-header-orient (a header side that is not drawn, the default side used; a custom header.formatType reports vl-format-type-custom; a header labelExpr is drawn and reports only its own unsupported constructs, see below); vl-concat-axis-shared, vl-composition-columns-ignored, and vl-repeat-ref-unresolved are produced from the view tree by the renderer and not by the catalog. The labelExpr of axes, legends, and facet headers (and of config.axis*, config.header*) is drawn: the identifier vl-expr-label is retired (never produced again and never reused) and a label expression reports only the vl-expr-function-name, vl-expr-view-state, and vl-expr-construct-name of its expression at the text of the expression (the format function of the number formats is on the whitelist and is evaluated: vl-expr-function-format is no longer reported, like vl-expr-label), while config.legend.labelExpr is not read, as in Vega-Lite 6.5. The xOffset and yOffset channels are supported channels, no longer reported as such; the catalog reports vl-offset-position (the position channel is missing, is quantitative, or is a temporal field without a time unit or with a day, weekday, binned, or maxbins unit, or the mark is a rect: the offset is ignored; a nominal or ordinal position with a time unit is an ordinary band parent and a temporal position with another time unit is the time unit parent, and neither is reported) and vl-offset-ranged (narrowed in Phase 14 to a continuous, quantitative or temporal, offset of a bar or an area that is not Vega-Lite's ranged offset, that is a temporal or binned offset, a position with x2 or y2, or a temporal position with a time unit: ignored; the ranged offset, an unbinned quantitative offset of a nominal or ordinal position without x2 or y2, is drawn and not reported) at the channel, and warns with vl-scale-type-ignored when a point scale type is given to a position that holds an offset. Phase 12 (milestone 1) narrows vl-expr-ref to an expression reference that is not evaluated (a site that Vega-Lite's schema does not allow, or a static site whose expression reads datum), scans the config of the top-level view as well, no longer reports the scale property domainRaw (which is supported), and words vl-param-variable as the variable parameters of a nested view being ignored (Vega-Lite compiles no signal for them). Phase 12 (milestone 2b) retires vl-encoding-bin-extent-param and vl-transform-bin-extent-param (the extent given by a parameter sets the span that chooses the bin step; the identifiers are never reused). Phase 13 retires vl-transform-regression, vl-transform-loess, vl-transform-density, vl-transform-quantile, vl-transform-extent, and vl-transform-pivot-op (the statistical transforms and every pivot operation are computed, so no transform of Vega-Lite is reported any more), never to be reused, and adds the warning vl-param-extent-static, which the ExpressionReferenceFolder produces for a static site that reads the parameter of an extent transform. Phase 13 also draws the image mark through the host's image resolver: Visit takes whether the caller supplied one and reports the image mark as vl-mark-image only without it (the warning vl-mark-image-unresolved is the painter's), accepts the url channel on the image mark (vl-channel-url on any other mark) and the secondary channels x2 and y2 on it, and checks it like every drawn mark. The Phase 13 remaining gaps retire vl-shape-path (a custom SVG path shape is drawn), vl-scale-interpolate-cubehelix, vl-encoding-impute (the impute of a channel other than x and y is ignored without a report, as Vega-Lite reads x and y only), vl-mark-invalid-show (the show and null invalid modes are drawn), vl-guide-legend-titleorient (every title orient is drawn), vl-facet-sort (a facet sort by an aggregate is applied), and the eight vl-guide-axis-name identifiers (labelBound, tickBand, tickExtra, position, translate, bandPosition, titleX, and titleY are drawn), never to be reused, and add the warning vl-shape-path-invalid (a shape that is neither a symbol name nor SVG path data that parses, drawn as a circle; path data without a command draws nothing and is reported too). vl-facet-field-transform and vl-composite-grouping are narrowed to a bin, an aggregate, and a binned or maxbins time unit (a time unit with parts is applied), and vl-guide-encode, and vl-format-type-custom remain. Phase 14 (hardening) retires vl-timeunit-binned (a binned time unit is read as it is, ends the bars of a rect, and floors in the timeUnit transform, as Vega-Lite 6.5 and Vega do), vl-timeunit-maxbins (the maxbins form in a predicate names no unit and compares the field), vl-facet-field-transform (the bin, aggregate, and time unit of a facet field are applied as the facet model of Vega-Lite applies them), and vl-composite-grouping (the bin, aggregate, and time unit of a grouping channel of a composite mark are transformed as extractTransformsFromEncoding does), never to be reused; vl-header-orient, vl-guide-encode, vl-format-type-custom, vl-offset-position (with its binned and maxbins parents), and vl-encoding-bandposition-rect remain. Phase 14 (expressions, legends, offsets, and invalid data) retires vl-guide-legend-clipheight (a clipHeight greater than 0 on a symbol legend is drawn; a gradient legend ignores it, as Vega does), never to be reused, narrows vl-offset-ranged to the continuous offsets of a bar or an area that are not ranged, and adds vl-scale-invalid-value (VisitConfigScaleInvalid: an entry of the config.scale.invalid of the specification that is neither "zero-or-min" nor an object with a number or text value, reported at the entry and ignored; the entries of the render-options configuration are not reported); the sampling functions random, sampleNormal, sampleLogNormal, and sampleUniform stay reported as vl-expr-function-name (the nine distribution functions are in the function table). */
        comment selectionRef /* Phase 12 (milestone 2): selection parameters are drawn in their initial state and no longer reported (vl-param-selection, vl-encoding-condition-param, and vl-transform-filter-param are retired and never produced again); the catalog reports, at the declaration, an animation selection (vl-param-selection-animation), a point selection over the identity of the rows with an initial value (vl-param-selection-id), and a selection that two or more layers of a layered view receive (vl-param-selection-layer, found with SelectionDeclarations.Assign), and ignores the interaction properties of a selection without a report; vl-param-selection-projection is a warning produced by the selection model. */
        comment sourceRef /* Source: src/DemaConsulting.CanvasNet.VegaLite/SpecModel/FeatureCatalog.cs */
                comment testRef /* Test: test/DemaConsulting.CanvasNet.VegaLite.Tests/SpecModel/FeatureCatalogTests.cs, FeatureCatalogTimeTests.cs, FeatureCatalogLayerTests.cs, FeatureCatalogCompositionTests.cs, FeatureCatalogCompositeTests.cs, and FeatureCatalogLabelExprAndOffsetTests.cs (the ranged-offset and the unreadable scale.invalid reports included), and FeatureCatalogImageTests.cs (and the catalog test of test/DemaConsulting.CanvasNet.VegaLite.Tests/Scales/MarkChannelGatingTests.cs) */
        comment designRef /* Design: docs/design/canvas-net-vega-lite/spec-model/feature-catalog.md */
        comment verificationRef /* Verification: docs/verification/canvas-net-vega-lite/spec-model/feature-catalog.md */
        comment reqRef /* Requirements: docs/reqstream/canvas-net-vega-lite/spec-model/feature-catalog.yaml */
    }
}
