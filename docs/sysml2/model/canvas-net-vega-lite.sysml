package CanvasNet {
    part def CanvasNetVegaLiteSystem {
        doc /* CanvasNetVegaLite is a static renderer for the public Vega-Lite specification language, delivered incrementally as the separate DemaConsulting.CanvasNet.VegaLite NuGet package. The public VegaLiteDocument unit parses Vega-Lite specification text from a string, a stream, or a file path (a VegaLiteSpecException with file, JSON pointer, line, and column for the first problem; an InvalidDataException for oversized source), describes the chart without drawing it (SchemaUrl, SchemaMajorVersion, Title, MarkTypes, DataReferences, ParameterNames), measures the size a chart renders at, and renders it onto a core Surface at its natural size times a scale or at an exact size (scaled uniformly to fit and centered). Rendering is static, deterministic (pixel-identical output, bundled Liberation fonts by default, UTC), and uses no network and no JavaScript runtime. Its public surface is VegaLiteDocument plus the VegaLiteOpenOptions, VegaLiteRenderOptions, VegaLiteLimits, VegaLiteFontOptions, VegaLiteLocation, VegaLiteDiagnostic, VegaLiteUnsupportedFeature, VegaLiteSize, VegaLiteDataReference, VegaLiteDataKind, VegaLiteSpecException, VegaLiteRenderException, and VegaLiteUnsupportedFeatureException types. The first delivery renders a single view with inline data: the marks bar, rect, point, circle, square, rule, and tick, the channels x, y, color, fill, stroke, size, and opacity, linear, band, and point scales, axes with d3 tick selection and number formatting, titles with subtitles, the Vega-Lite default theme and configuration (the defaults of version 6, applied to version 5 and 6 specifications), and a view layout with padding and autosize of pad or none. Phase 4 adds the data sources of that single view: local CSV, TSV, DSV, and JSON files read under the caller's file-access policy (VegaLiteOpenOptions.FileAccess, every regular local file by default; relative to the folder of the opened specification or extra data paths, which are search locations rather than boundaries, or through the caller's file callback; strict bounded UTF-8), named datasets (the caller's Datasets option before the top-level datasets of the specification), generated sequences, format.parse conversions and per-column type inference (ISO 8601 dates in UTC), and format.property; a local file that cannot be used fails the render with a VegaLiteRenderException, and remote URLs are reported (vl-data-remote-url) and never fetched. Every recognized construct that is not drawn is reported with a stable vl- identifier and its location, never skipped silently, and strict mode throws at the first report. The internal VegaLiteSpecModel subsystem contains the SpecParser unit (UTF-8 JSON to an immutable tree with pointers and locations under size and depth limits), the FeatureCatalog unit (the stable vl- reports), and the ConfigResolver unit (the Vega and Vega-Lite defaults merged with the specification's and the caller's configuration). The internal VegaLiteData subsystem contains the DataTable unit (typed values, including UTC dates and the immutable array, object, and regular expression values that expressions produce, and tables), the DataLoader unit (inline rows, local files, named datasets, and sequences under data limits, and the lookup sources and derived-row reservations of the transforms through the same per-call budget), the DataFileResolver unit (the policy-checked, bounded reading of local data files), and the DelimitedTextParser unit (CSV, TSV, and DSV, the parse conversions, and the type inference). Phase 5 adds the expression language and the row transforms: the internal VegaLiteExpressions subsystem contains the ExpressionParser unit (a bounded single-pass compiler of a closed subset of the Vega expression language into an immutable program, with located errors that name the offset inside the text), the ExpressionEvaluator unit (a non-recursive, culture-invariant interpreter with JavaScript coercion under a shared evaluation-step budget), and the ExpressionFunctions unit (the closed table of 57 pure whitelisted functions with a non-backtracking regular expression translation); the internal VegaLiteTransforms subsystem contains the RowTransforms unit (calculate, filter with predicates, fold, flatten, sample with a deterministic seed, pivot, and lookup, run eagerly after the DataLoader and before the scales, together with the static variable parameter environment, under the row, field, string, and step limits). Expressions are evaluated per row only for calculate, filter, and the row-bound color, opacity, width, and size values of marks and encodings; static variable parameters (a value or an expression, overridable through the Parameters render option) are supported, while selection parameters, event bindings, conditions on a parameter, the statistical transforms, and the format (other than the time formats), color, geographic, and view-state expression functions remain deferred and are reported (the time-unit transform and the date and time functions were added in Phase 8). Phase 6 adds, in the same Transforms subsystem, the AggregateTransforms unit (aggregate with all 24 operations, joinaggregate, window, bin, stack, and impute, with structural group keys and a deterministic bootstrap) and the EncodingPlan unit (the implicit bin, aggregate, stack, titles, and raw and main tables of the encoding of a chart), so that histograms, aggregated and stacked bars, binned and ranged rects, and categories sorted by an aggregate are drawn with bin-aware axes. Phase 7 adds legends and color: symbol, gradient, and discrete gradient legends (LegendBuilder and LegendLayout) for the color, fill, stroke, size, shape, opacity, stroke width, and stroke dash channels, the 68 Vega color schemes with their notices, interpolation in several color spaces, the sequential, diverging, quantile, quantize, threshold, bin-ordinal, log, pow, sqrt, and symlog scales, the shape, stroke width, stroke dash, fill opacity, stroke opacity, and angle channels, binning of the channels that have a scale, and conditional encodings with a test; a legend encode, custom format type, and clip height, and the scale properties bins and domainRaw, and conditions on a parameter remain reported (the cubehelix interpolation, custom SVG path shapes, and the legend title orient are drawn since Phase 13). The SpecParser unit also compiles the expressions and validates the parameters and transforms when a document is opened (SpecParser.Transforms.cs and SpecExpressions.cs), and the ScaleResolver unit orders a category by an aggregate of the transformed rows. Phase 8 adds time: the TimeCalendar unit (instants in the years 1 to 9999 and civil parts in one caller-chosen time zone, UTC by default, with the ECMAScript rule for the wall times of a daylight saving change; the d3-time intervals; the Vega-Lite time units and datetime objects) and the TimeFormat unit (the d3-time-format formatter and parser in the English locale, the Vega multi-format, and the JavaScript Date.parse rules) of the Data subsystem, the TimeUnitTransform unit of the Transforms subsystem (the start and end fields of a time unit and the fields that are implicitly parsed as dates), the TimeLabels unit of the Guides subsystem (the label rules of time axes and legends), the date and time expression functions, the time and UTC scales with the d3 time ticks, time axes and temporal legends, and bars and rects that span their time unit; the public API is unchanged and the TimeZone render option, which was reserved, now decides every local date computation. The internal VegaLiteScales subsystem contains the ScaleModel, ScaleResolver, Ticks, NumberFormat, ColorSchemes, and ColorInterpolator units. The internal VegaLiteGuides subsystem contains the TextMeasurer, TitleBuilder, AxisBuilder, LabelOverlap, LegendBuilder, TimeLabels, and LabelExpressions units. The internal VegaLiteLayout subsystem contains the ViewLayout, LegendLayout, and CompositionLayout units. The internal VegaLiteMarks subsystem contains the MarkBuilder and CurveBuilder units. The internal VegaLiteScenegraph subsystem contains the VegaLiteSceneModel, ScenePainter, ArcGeometry, CssPaint, and SymbolPathParser units. Phase 9 adds the marks line, area, trail, text, and arc: the line, area, and trail marks are paths (grouped by the grouping channels, sorted by the position or the order channel, interpolated by the CurveBuilder unit - the d3-shape curves of the fifteen Vega-Lite interpolate values - and drawn as ScenePath segments or a SceneTrail), with the point and line overlays, the invalid-data modes (break-paths by default, filter), and the implicit impute of stacked layers; the text mark draws formatted labels (d3 number and time formats) with polar offsets; the arc mark draws pie, donut, and radial slices from the polar theta and radius channels (the polar stack of the EncodingPlan unit, the polar scales of the ScaleResolver unit) through the d3-shape arc geometry of the ArcGeometry unit; the order channel decides the draw order of every mark; the encoding impute of x and y is executed; the stroke dash offset, cap, join, and miter limit reach every item; the legend symbols of the new marks follow Vega-Lite (a stroke for a line, a rule, and a trail, a filled circle for an area, an arc, and a text). The public API is unchanged, and the geoshape and image marks stay reported. Phase 10 draws the layer composition (the SpecNormalizer unit of the SpecModel subsystem reduces the views to the layers that are drawn, with the data, transform, encoding, and size that a layer inherits; the layers share one scale by default over the union of their domains, or keep scales, axes, and legends apart with resolve; the guides of the layers are merged or kept apart as Vega-Lite does; a step sizes the combined categories; MaxViews and MaxCompositionDepth are enforced) and the composite marks boxplot, errorbar, and errorband, which are expanded into the primitive layers that Vega-Lite normalizes them to, and a transform of a layered view is applied and no longer reported. Phase 11 draws the compositions (the SpecNormalizer unit reduces concat, hconcat, vconcat, facet, and repeat to a view tree; the CompositionLayout unit of the Layout subsystem places the cells of a concatenation or a facet in a grid with headers, footers, and titles; the facet and row/column channels partition the rows of the cells; the data, transform, and encoding of a composition are inherited by its charts; scales, axes, and legends are shared or kept apart by resolve; MaxViews and MaxCompositionDepth cover every kind), the autosize types fit, fit-x, and fit-y, and the container width and height, and makes the carry-over of the first explicit domain of the layers a union. A later release draws the labelExpr of axes, legends, and facet headers (the LabelExpressions unit of the Guides subsystem; the diagnostic vl-expr-label is retired and never reused, so label expressions report only the unsupported functions and constructs of their expression at its text) and the xOffset and yOffset channels (grouped bars and offset points through nested band, point, linear, or time offset scales of the ScaleResolver unit, the offset placement of the MarkBuilder unit, the offset groups of the stack and aggregate of the EncodingPlan unit, and the reports vl-offset-position and vl-offset-ranged of the FeatureCatalog unit). Selection parameters, conditions on a parameter, the statistical transforms, and the parts of a facet field (a bin, timeUnit, or aggregate of the field, a sort by an aggregate, a header orient) remain deferred and are reported (legends, local data files, named datasets, sequences, expressions, static parameters, the row transforms, the aggregation, binning, and stacking above, the time phase, and the line, area, trail, text, and arc marks - paths with the fifteen interpolations, overlays, invalid-data modes, labels, and pie, donut, and radial charts - are supported) - see docs/design/canvas-net-vega-lite.md's Design Constraints (Supported And Deferred Features, Deliberate Strictness And Deviations) and Implementation Phase Plan. Phase 12 (milestone 1 of 3: expression-reference folding, the parameter hoist, and the variable-parameter domains) adds the ExpressionReferenceFolder unit of the SpecModel subsystem (the expr references of the static sites - the title, the padding and background, the guides, scales, and marks that no row reads, and the configuration - are compiled when the document is opened and evaluated once per call with the parameters at their initial state), evaluates the parameters first in every call, lets the Parameters render option take arrays and objects, takes the domain of a scale as it is from domainRaw or from the variable parameter that scale.domain names (clipping the marks, reporting an unusable value as vl-scale-domain-raw), narrows vl-expr-ref, retires vl-scale-property-domainRaw, and words vl-param-variable as the ignored variable parameters of a nested view. Phase 12 (milestones 2a and 2b) draws selection parameters in their initial state (the SelectionModel unit: stores and resolved values, the selection functions of the expression engine, conditions and filters on a selection, the caller's initial value, the brush marks of an interval selection with an initial value, bind scales as the domain and clip of the continuous scales, a selection as scale.domain, the extent of a bin given by a parameter as the span of its step, and the config.selection defaults), retires vl-encoding-bin-extent-param and vl-transform-bin-extent-param, and leaves the lookup source given by a parameter (vl-transform-lookup-param) reported. Phase 12 (milestone 3) draws the legend that a selection is bound to (bind legend) in its initial state: the symbols and labels of the entries that the selection does not hold take config.legend.unselectedOpacity (the LegendDimming type of the LegendBuilder unit). Phase 14 adds, in the units that own them: the nine probability distribution functions of the expression language (ExpressionFunctions.Distributions.cs, 113 functions in all; random and the sample functions stay unsupported because an expression is a pure deterministic function), the clipHeight of a symbol legend (LegendBuilder, vl-guide-legend-clipheight retired), the ranged offsets of a bar or an area (the ScaleResolver, MarkBuilder, and AxisBuilder units; vl-offset-ranged narrowed to the continuous offsets that are not ranged), and the config.scale.invalid entries of a channel (MarkBuilder and ScaleModel; the new report vl-scale-invalid-value of the FeatureCatalog unit). */

        comment testRef /* Test: test/DemaConsulting.CanvasNet.VegaLite.Tests/VegaLiteSystemIntegrationTests.cs, test/DemaConsulting.CanvasNet.VegaLite.Tests/VegaLiteChartIntegrationTests.cs, test/DemaConsulting.CanvasNet.VegaLite.Tests/VegaLiteAggregationIntegrationTests.cs, test/DemaConsulting.CanvasNet.VegaLite.Tests/VegaLiteTimeIntegrationTests.cs, test/DemaConsulting.CanvasNet.VegaLite.Tests/VegaLiteTemporalScaleTests.cs, test/DemaConsulting.CanvasNet.VegaLite.Tests/VegaLiteLineAreaIntegrationTests.cs, test/DemaConsulting.CanvasNet.VegaLite.Tests/VegaLiteArcTextIntegrationTests.cs, the hardening suite test/DemaConsulting.CanvasNet.VegaLite.Tests/Hardening/ (VegaLiteFuzzTests.cs, VegaLiteLimitAuditTests.cs, VegaLiteSourceGuardTests.cs, VegaLiteDeterminismTests.cs), test/DemaConsulting.CanvasNet.VegaLite.Tests/VegaLitePhase14SystemTests.cs */
        comment designRef /* Design: docs/design/canvas-net-vega-lite.md */
        comment verificationRef /* Verification: docs/verification/canvas-net-vega-lite.md */
        comment reqRef /* Requirements: docs/reqstream/canvas-net-vega-lite.yaml */
        comment /* Third-Party Provenance and Attribution: CanvasNetVegaLite is derived with attribution, not clean-room. Default values and algorithms are ported from Vega and Vega-Lite (BSD-3-Clause) and from d3-array, d3-format, d3-scale, d3-time, d3-time-format, and d3-scale-chromatic (ISC); the license texts ship in the package under licenses, the provenance record is src/DemaConsulting.CanvasNet.VegaLite/third-party/README.md, and every source file with ported logic carries a header comment pointing to it. No upstream source file, test, example, or dataset is copied, and the package is not affiliated with or endorsed by the Vega, Vega-Lite, or D3 projects - see the Third-Party Provenance and Attribution constraint in docs/design/canvas-net-vega-lite.md. */
        comment /* CanvasNetVegaLite references the sibling CanvasNet system (its Canvas subsystem, for the Surface that Render returns and the Rgba32 colors; its Geometry subsystem, for the Path and PathBuilder of symbols, rectangles, and strokes; its Drawing subsystem, for PathFiller and PathStroker; its Fonts subsystem, for TrueTypeFont, SystemFontCatalog, and the bundled Liberation fonts; its Files subsystem, for the FileReferenceResolver behind every local data file, under the FileAccessPolicy of VegaLiteOpenOptions.FileAccess; and its Rendering subsystem, for TextRenderer text measurement and drawing) through a ProjectReference in its csproj - modeled below as non-owning dependency relationships, since both systems live in this same git repository (each distributed as its own NuGet package, with the core package listed as the dependency of the VegaLite package) rather than being third-party (OTS) or Shared Package dependencies. All parsing, layout, scale, tick, and formatting logic is its own code on the BCL. CanvasNetVegaLite must never reference CanvasNetCharts, CanvasNetSvg, CanvasNetPdf, CanvasNetPptx, CanvasNetVsdx, CanvasNetRender3D, or CanvasNetScad - see the CanvasNetVegaLite System Design document's Dependencies section. */

        part vegaLiteDocument : VegaLiteDocument;
        part vegaLiteSpecModel : VegaLiteSpecModel;
        part vegaLiteData : VegaLiteData;
        part vegaLiteExpressions : VegaLiteExpressions;
        part vegaLiteTransforms : VegaLiteTransforms;
        part vegaLiteScales : VegaLiteScales;
        part vegaLiteGuides : VegaLiteGuides;
        part vegaLiteLayout : VegaLiteLayout;
        part vegaLiteMarks : VegaLiteMarks;
        part vegaLiteScenegraph : VegaLiteScenegraph;

        dependency usesCanvas from CanvasNetVegaLiteSystem to Canvas;
        dependency usesDrawing from CanvasNetVegaLiteSystem to Drawing;
        dependency usesFiles from CanvasNetVegaLiteSystem to Files;
        dependency usesFonts from CanvasNetVegaLiteSystem to Fonts;
        dependency usesGeometry from CanvasNetVegaLiteSystem to Geometry;
        dependency usesRendering from CanvasNetVegaLiteSystem to Rendering;
        dependency usesImageSources from CanvasNetVegaLiteSystem to ImageSources;
    }
}
