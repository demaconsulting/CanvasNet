package CanvasNet {
    part def PdfDocument {
        doc /* PDF document parser and page-rendering codec: parses cross-references, trailer, and page tree, reports page count/size/rotation, and interprets each page's content stream (path construction/painting/clipping/shading, graphics-state stack, device color operators, CIE-based (CalGray/CalRGB/Lab) and ICCBased (resolved through /N or /Alternate; profile data is never applied) color spaces, Separation/DeviceN/Indexed color spaces evaluated through tint-transform functions (FunctionType 0 including multi-input, 2, 3 and 4 PostScript calculator), generalized stream filter pipeline, image XObjects (raw, DCTDecode, CCITTFaxDecode and JPXDecode samples, /Decode, /SMask soft masks and JPX /SMaskInData; device-aligned images are composited with geometric rectangle-clip coverage so an image edge coincident with a clip edge keeps its full ink), and (Phase 4) simple TrueType font resolution/encoding and text-object/positioning/showing operators, with (Phase 6) automatic system/bundled-Liberation font-fallback substitution for a non-embedded font) to render real path geometry, images, and glyph outlines onto the returned Surface in real device color. The unit also covers PdfImageSource (the IImageSource for .pdf files: the page the fragment of the link names with page=N, else the first, fitted inside the placement over a transparent background) for the shared image resolver of the core ImageSources subsystem. */

        comment sourceRef /* Source: src/DemaConsulting.CanvasNet.Pdf/PdfImageSource.cs, src/DemaConsulting.CanvasNet.Pdf/PdfDocument.cs, src/DemaConsulting.CanvasNet.Pdf/PdfDocument.Tokenizer.cs, src/DemaConsulting.CanvasNet.Pdf/PdfDocument.ObjectModel.cs, src/DemaConsulting.CanvasNet.Pdf/PdfDocument.Xref.cs, src/DemaConsulting.CanvasNet.Pdf/PdfDocument.PageTree.cs, src/DemaConsulting.CanvasNet.Pdf/PdfDocument.ContentStream.cs, src/DemaConsulting.CanvasNet.Pdf/PdfDocument.GraphicsState.cs, src/DemaConsulting.CanvasNet.Pdf/PdfDocument.PathOps.cs, src/DemaConsulting.CanvasNet.Pdf/PdfDocument.Color.cs, src/DemaConsulting.CanvasNet.Pdf/PdfDocument.ColorKernel.cs, src/DemaConsulting.CanvasNet.Pdf/PdfDocument.Filters.cs, src/DemaConsulting.CanvasNet.Pdf/PdfDocument.Filters.Lzw.cs, src/DemaConsulting.CanvasNet.Pdf/PdfDocument.Filters.Ascii.cs, src/DemaConsulting.CanvasNet.Pdf/PdfDocument.Filters.RunLength.cs, src/DemaConsulting.CanvasNet.Pdf/PdfDocument.Images.cs, src/DemaConsulting.CanvasNet.Pdf/PdfDocument.Fonts.cs, src/DemaConsulting.CanvasNet.Pdf/PdfDocument.Fonts.ToUnicode.cs, src/DemaConsulting.CanvasNet.Pdf/PdfDocument.Fonts.Type0.cs, src/DemaConsulting.CanvasNet.Pdf/PdfDocument.Fonts.Type1.cs, src/DemaConsulting.CanvasNet.Pdf/PdfDocument.Fonts.Type3.cs, src/DemaConsulting.CanvasNet.Pdf/PdfDocument.FontFallback.cs, src/DemaConsulting.CanvasNet.Pdf/PdfDocument.Text.cs, src/DemaConsulting.CanvasNet.Pdf/PdfDocument.CcittFax.cs, src/DemaConsulting.CanvasNet.Pdf/PdfDocument.Encryption.cs, src/DemaConsulting.CanvasNet.Pdf/PdfDocument.Functions.cs, src/DemaConsulting.CanvasNet.Pdf/PdfDocument.Functions.PostScript.cs, src/DemaConsulting.CanvasNet.Pdf/PdfDocument.Patterns.cs, src/DemaConsulting.CanvasNet.Pdf/PdfDocument.Patterns.Shading.cs, src/DemaConsulting.CanvasNet.Pdf/PdfDocument.Patterns.Shading.Mesh.cs, src/DemaConsulting.CanvasNet.Pdf/PdfDocument.Patterns.Tiling.cs, src/DemaConsulting.CanvasNet.Pdf/PdfPageInfo.cs, src/DemaConsulting.CanvasNet.Pdf/PdfRenderOptions.cs, src/DemaConsulting.CanvasNet.Pdf/NamespaceDoc.cs */
        comment testRef /* Test: test/DemaConsulting.CanvasNet.Pdf.Tests/PdfImageSourceTests.cs, test/DemaConsulting.CanvasNet.Pdf.Tests/PdfDocumentTests.cs, test/DemaConsulting.CanvasNet.Pdf.Tests/PdfDocumentColorSpaceTests.cs, test/DemaConsulting.CanvasNet.Pdf.Tests/PdfDocumentTintTests.cs, test/DemaConsulting.CanvasNet.Pdf.Tests/PdfDocumentShadingFidelityTests.cs, test/DemaConsulting.CanvasNet.Pdf.Tests/PdfSystemIntegrationTests.cs, test/DemaConsulting.CanvasNet.Pdf.Tests/PdfFixtureTests.cs, test/DemaConsulting.CanvasNet.Pdf.Tests/PdfDocumentEncryptionTests.cs, test/DemaConsulting.CanvasNet.Pdf.Tests/PdfDocumentMeshShadingTests.cs, test/DemaConsulting.CanvasNet.Pdf.Tests/PdfDocumentSymbolicEncodingTests.cs, test/DemaConsulting.CanvasNet.Pdf.Tests/PdfDocumentJpxTests.cs, test/DemaConsulting.CanvasNet.Pdf.Tests/PdfImageResamplingTests.cs, test/DemaConsulting.CanvasNet.Pdf.Tests/PdfDocumentImageColorConversionTests.cs, test/DemaConsulting.CanvasNet.Pdf.Tests/PdfDocumentImageDownscaleTests.cs, test/DemaConsulting.CanvasNet.Pdf.Tests/PdfDocumentClipEdgeInkTests.cs, test/DemaConsulting.CanvasNet.Pdf.Tests/PdfDocumentThinBarInkTests.cs, test/DemaConsulting.CanvasNet.Pdf.Tests/PdfDocumentThinRuleInkTests.cs, test/DemaConsulting.CanvasNet.Pdf.Tests/PdfDocumentHairlineStrokeTests.cs, test/DemaConsulting.CanvasNet.Pdf.Tests/PdfDocumentSurfaceOwnershipTests.cs */
        comment designRef /* Design: docs/design/canvas-net-pdf/pdf-document.md */
        comment verificationRef /* Verification: docs/verification/canvas-net-pdf/pdf-document.md */
        comment reqRef /* Requirements: docs/reqstream/canvas-net-pdf/pdf-document.yaml */
    }
}
