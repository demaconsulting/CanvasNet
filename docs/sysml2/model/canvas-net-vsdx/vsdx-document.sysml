package CanvasNet {
    /* cspell:ignore vsdx Visio VisioML xfrm stencil stencils glueable NURBS nurbs shapesheet ShapeSheet */
    /* cspell:ignore PinX PinY LocPinX LocPinY FlipX FlipY BeginX BeginY EndX EndY MasterShape */
    /* cspell:ignore FillForegnd FillBkgnd LineColor LineWeight LinePattern FillPattern */
    /* cspell:ignore TxtPinX TxtPinY TxtLocPinX TxtLocPinY TxtWidth TxtHeight TxtAngle */
    part def VsdxDocument {
        doc /* OPC (Open Packaging Conventions) package parser and VisioML diagram-rendering codec. Opens a .vsdx file as a read-only ZipArchive, resolves [Content_Types].xml and the _rels/.rels -> visio/document.xml -> masters.xml/pages.xml/theme1.xml relationship chain (including per-page and per-master .rels indirection, resolved exclusively through r:id references, never by filename-number convention), and parses visio/document.xml's <StyleSheets> (no <Colors>/<FaceNames> extension table is parsed) and visio/pages/pages.xml's page index. Resolves a page's full shape tree: Master/MasterShape cell-and-geometry-row inheritance (an instance cell with a non-Inh F wins; an instance cell with F="Inh" or no cell at all falls through to the resolved master value; a geometry row is matched and merged, or marked deleted, by IX; a Group master shape recurses per child via MasterShape, matched by ID not position); the StyleSheet chain for LineStyle/FillStyle/TextStyle (walking each StyleSheet's own parent reference until a literal, non-Inh value is found, terminating at StyleSheet ID 0 "No Style", with a literal "Themed" value resolved against an optional parsed theme; a bare THEMEVAL() "Themed" line/fill/text-color cell, which names no theme slot, takes the same cell's value from the built-in "No Style" StyleSheet (ID 0) instead; a bare "Themed" character Font resolves to the theme's minor Latin typeface, then StyleSheet 0's Font; a neutral default - gray for a color, Arial for a font - applies only when none of these supplies a value, and an unresolvable themed color is reported as the vsdx-themed-color unsupported feature); shape geometry (MoveTo/LineTo/RelMoveTo/RelLineTo rows resolved into the core Path type; EllipticalArcTo/ArcTo rows converted to an ArcTo path command reaching the row's own destination point, with a zero-bow ArcTo row degrading to a plain LineTo; PolylineTo/NURBSTo/SplineStart-SplineKnot rows flattened to line segments (a clamped rational B-spline sampled with de Boor's algorithm, honoring xType/yType and degree, bounded by hard caps of 1024 control points, degree 25 and 4096 segments; an unevaluable spline degrades to a polyline and is reported as vsdx-geometry-spline-approximated; a malformed or over-cap row is skipped and reported); a group child with its own Master reference inherits that master's shape; InfiniteLine and any other unrecognized row type tolerantly skipped and reported rather than approximated; a Master/instance geometry-row merge by matching IX is cell-by-cell, not whole-row-replacement); the shape-local-to-page affine transform (translate by LocPinX/Y, apply FlipX/FlipY, rotate by Angle in radians, translate by PinX/PinY - identical for a 2-D shape and a 1-D connector, whose own PinX/PinY/Width/Height/Angle are themselves pre-derived by Visio at save time from BeginX/Y/EndX/Y); text (<Text> run parsing against Section N="Character"/"Paragraph" rows, including a <fld> Field-reference element's own nested text content parsed as a literal run, and TxtPinX/Y/TxtLocPinX/Y/TxtWidth/Height/TxtAngle text-box positioning); and connector/glue-point routing (<Connects> parsing, trusting a connector's own pre-baked, already-resolved BeginX/Y/EndX/Y page-space coordinates rather than performing live glue-point tracking). Implements the public, page-level Render API: VsdxDocument.Render(int pageIndex, int width, int height, VsdxRenderOptions? options) and a DPI convenience overload, which clear the destination Surface to VsdxRenderOptions.BackgroundColor (default opaque white) and walk a page's shape tree in document order (first shape drawn first/bottom), painting each node's resolved fill, stroke, connector line/arrowheads, and text - suppressing only a shape's own text paint, not its fill/stroke/children, when its effective HideText cell resolves truthy - composing a group's own already-resolved child transform exactly as described above, with no separate chOff/chExt-style child-coordinate remap step, since a VisioML group child's cells are already expressed directly in the parent group's own local box. Recognized BeginArrow/EndArrow indices include a hollow/unfilled-triangle style (index 254, confirmed in use in real-world content). A non-solid FillPattern beyond the documented subset instead degrades to the same solid-fill treatment as FillPattern="1", using the shape's own resolved FillForegnd color, never throwing and reported as a vsdx-fill-pattern-N unsupported feature; an embedded Foreign shape (image/OLE object) carries no distinct Type-based handling at all and is resolved exactly like any other Shape element (its own geometry/paint/text, when present, render normally; VsdxUnsupportedFeatureException is thrown only when VsdxRenderOptions.ThrowOnUnsupportedFeature opts in); an unrecognized BeginArrow/EndArrow index or an unrecognized geometry row type instead degrades to a tolerant, no-effect skip that is reported (never silently) to VsdxRenderOptions.UnsupportedFeatureHandler as a stable feature token (VsdxUnsupportedFeature) once per distinct feature per Render call; a dangling Connect target is likewise skipped tolerantly but is not reported. The unit also covers VsdxImageSource (the IImageSource for .vsdx files: the page the fragment of the link names with page=N, else the first, fitted inside the placement over a transparent background, unsupported features reported) for the shared image resolver of the core ImageSources subsystem. */

        comment sourceRef /* Source: src/DemaConsulting.CanvasNet.Vsdx/VsdxImageSource.cs, src/DemaConsulting.CanvasNet.Vsdx/VsdxDocument.cs, src/DemaConsulting.CanvasNet.Vsdx/VsdxDocument.Package.cs, src/DemaConsulting.CanvasNet.Vsdx/NamespaceDoc.cs, src/DemaConsulting.CanvasNet.Vsdx/VsdxDocument.Pages.cs, src/DemaConsulting.CanvasNet.Vsdx/VsdxPageInfo.cs, src/DemaConsulting.CanvasNet.Vsdx/VsdxDocument.Masters.cs, src/DemaConsulting.CanvasNet.Vsdx/VsdxDocument.CellMerge.cs, src/DemaConsulting.CanvasNet.Vsdx/VsdxCell.cs, src/DemaConsulting.CanvasNet.Vsdx/VsdxCellBag.cs, src/DemaConsulting.CanvasNet.Vsdx/VsdxDocument.Styles.cs, src/DemaConsulting.CanvasNet.Vsdx/VsdxDocument.Theme.cs, src/DemaConsulting.CanvasNet.Vsdx/VsdxTheme.cs, src/DemaConsulting.CanvasNet.Vsdx/VsdxColorPalette.cs, src/DemaConsulting.CanvasNet.Vsdx/VsdxShapeNode.cs, src/DemaConsulting.CanvasNet.Vsdx/VsdxDocument.Shapes.cs, src/DemaConsulting.CanvasNet.Vsdx/VsdxDocument.Groups.cs, src/DemaConsulting.CanvasNet.Vsdx/VsdxGeometry.cs, src/DemaConsulting.CanvasNet.Vsdx/VsdxDocument.Geometry.cs, src/DemaConsulting.CanvasNet.Vsdx/VsdxDocument.Splines.cs, src/DemaConsulting.CanvasNet.Vsdx/VsdxDocument.Transform.cs, src/DemaConsulting.CanvasNet.Vsdx/VsdxShapeTransform.cs, src/DemaConsulting.CanvasNet.Vsdx/VsdxDocument.Paint.cs, src/DemaConsulting.CanvasNet.Vsdx/VsdxResolvedPaint.cs, src/DemaConsulting.CanvasNet.Vsdx/VsdxDocument.Text.cs, src/DemaConsulting.CanvasNet.Vsdx/VsdxDocument.TextBox.cs, src/DemaConsulting.CanvasNet.Vsdx/VsdxTextBoxTransform.cs, src/DemaConsulting.CanvasNet.Vsdx/VsdxDocument.TextStyle.cs, src/DemaConsulting.CanvasNet.Vsdx/VsdxDocument.TextLayout.cs, src/DemaConsulting.CanvasNet.Vsdx/VsdxTextLayout.cs, src/DemaConsulting.CanvasNet.Vsdx/VsdxTextRun.cs, src/DemaConsulting.CanvasNet.Vsdx/VsdxDocument.TextRender.cs, src/DemaConsulting.CanvasNet.Vsdx/VsdxConnect.cs, src/DemaConsulting.CanvasNet.Vsdx/VsdxConnectorEndpoints.cs, src/DemaConsulting.CanvasNet.Vsdx/VsdxDocument.Connects.cs, src/DemaConsulting.CanvasNet.Vsdx/VsdxArrowhead.cs, src/DemaConsulting.CanvasNet.Vsdx/VsdxArrowheadGeometry.cs, src/DemaConsulting.CanvasNet.Vsdx/VsdxDocument.Arrowheads.cs, src/DemaConsulting.CanvasNet.Vsdx/VsdxUnsupportedFeatureException.cs, src/DemaConsulting.CanvasNet.Vsdx/VsdxRenderOptions.cs, src/DemaConsulting.CanvasNet.Vsdx/VsdxDocument.Render.cs, src/DemaConsulting.CanvasNet.Vsdx/VsdxDocument.Diagnostics.cs, src/DemaConsulting.CanvasNet.Vsdx/VsdxUnsupportedFeature.cs */
        comment testRef /* Test: test/DemaConsulting.CanvasNet.Vsdx.Tests/VsdxImageSourceTests.cs, test/DemaConsulting.CanvasNet.Vsdx.Tests/VsdxDocumentTests.cs, test/DemaConsulting.CanvasNet.Vsdx.Tests/VsdxSystemIntegrationTests.cs, test/DemaConsulting.CanvasNet.Vsdx.Tests/VsdxGeometryTests.cs, test/DemaConsulting.CanvasNet.Vsdx.Tests/VsdxTransformTests.cs, test/DemaConsulting.CanvasNet.Vsdx.Tests/VsdxMasterInheritanceTests.cs, test/DemaConsulting.CanvasNet.Vsdx.Tests/VsdxStyleResolutionTests.cs, test/DemaConsulting.CanvasNet.Vsdx.Tests/VsdxColorPaletteTests.cs, test/DemaConsulting.CanvasNet.Vsdx.Tests/VsdxThemeResolutionTests.cs, test/DemaConsulting.CanvasNet.Vsdx.Tests/VsdxTextParsingTests.cs, test/DemaConsulting.CanvasNet.Vsdx.Tests/VsdxTextLayoutTests.cs, test/DemaConsulting.CanvasNet.Vsdx.Tests/VsdxTextRenderTests.cs, test/DemaConsulting.CanvasNet.Vsdx.Tests/VsdxTextStyleTests.cs, test/DemaConsulting.CanvasNet.Vsdx.Tests/VsdxTextBoxPositioningTests.cs, test/DemaConsulting.CanvasNet.Vsdx.Tests/VsdxConnectsParsingTests.cs, test/DemaConsulting.CanvasNet.Vsdx.Tests/VsdxGluePointResolutionTests.cs, test/DemaConsulting.CanvasNet.Vsdx.Tests/VsdxArrowheadResolutionTests.cs, test/DemaConsulting.CanvasNet.Vsdx.Tests/VsdxGroupResolutionTests.cs, test/DemaConsulting.CanvasNet.Vsdx.Tests/VsdxRenderTests.cs, test/DemaConsulting.CanvasNet.Vsdx.Tests/VsdxConnectorFixtureTests.cs, test/DemaConsulting.CanvasNet.Vsdx.Tests/VsdxFixtureShapeResolutionTests.cs, test/DemaConsulting.CanvasNet.Vsdx.Tests/VsdxFixtureTextResolutionTests.cs, test/DemaConsulting.CanvasNet.Vsdx.Tests/VsdxRenderFixtureTests.cs, test/DemaConsulting.CanvasNet.Vsdx.Tests/VsdxUnsupportedFeatureTests.cs, test/DemaConsulting.CanvasNet.Vsdx.Tests/VsdxCurveGeometryTests.cs, test/DemaConsulting.CanvasNet.Vsdx.Tests/VsdxThemedFallbackTests.cs - against the fixture corpus in test/DemaConsulting.CanvasNet.Vsdx.Tests/VsdxFixtures/. */
        comment designRef /* Design: docs/design/canvas-net-vsdx/vsdx-document.md */
        comment verificationRef /* Verification: docs/verification/canvas-net-vsdx/vsdx-document.md */
        comment reqRef /* Requirements: docs/reqstream/canvas-net-vsdx/vsdx-document.yaml */
    }
}
