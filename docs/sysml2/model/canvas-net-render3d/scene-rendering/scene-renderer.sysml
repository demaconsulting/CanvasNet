package CanvasNet {
    part def SceneRenderer {
        doc /* The public static SceneRenderer (Render and RenderFitted) and immutable, init-validated SceneRenderOptions (including the MaxFragmentsPerTile budget and the UnsupportedFeatureHandler / ThrowOnUnsupportedFeature diagnostics options), the public RenderBudgetExceededException, SceneRenderUnsupportedFeature, and SceneRenderUnsupportedFeatureException diagnostics, plus the internal CsgOperandValidator, TileBinner, SampleResolver, and TileWorkspace: validates arguments, flattens the scene, compiles the CsgNode tree and selects the unchanged z-buffer path for opaque union-only scenes without overlays or the fragment-list path (driving FragmentBuffer and CsgResolver; used for CSG, translucent NodeAppearance alpha, and OverlayNode bodies, with the appearance alpha carried on the triangle shades) otherwise, reports open, non-manifold, inconsistently wound, degenerate, or inverted (shell wound against its nesting) CSG, translucent, and overlay operands on position-welded meshes (an explicit near plane or a camera inside an operand is supported and not reported), sets up and bins triangles into fixed 32x32-pixel tiles, resolves each tile with a bounded per-worker workspace, resolves k-by-k ordered-grid supersamples with a premultiplied-alpha box filter (honoring background alpha) into the output Surface, runs tiles in parallel with output bit-identical to sequential rendering, and cooperatively cancels with a plain OperationCanceledException. */

        comment sourceRef /* Source: src/DemaConsulting.CanvasNet.Render3D/SceneRendering/SceneRenderer.cs, src/DemaConsulting.CanvasNet.Render3D/SceneRendering/SceneRenderOptions.cs, src/DemaConsulting.CanvasNet.Render3D/SceneRendering/RenderBudgetExceededException.cs, src/DemaConsulting.CanvasNet.Render3D/SceneRendering/SceneRenderUnsupportedFeature.cs, src/DemaConsulting.CanvasNet.Render3D/SceneRendering/SceneRenderUnsupportedFeatureException.cs, src/DemaConsulting.CanvasNet.Render3D/SceneRendering/CsgOperandValidator.cs, src/DemaConsulting.CanvasNet.Render3D/SceneRendering/TileBinner.cs, src/DemaConsulting.CanvasNet.Render3D/SceneRendering/SampleResolver.cs, src/DemaConsulting.CanvasNet.Render3D/SceneRendering/TileWorkspace.cs */
        comment testRef /* Test: test/DemaConsulting.CanvasNet.Render3D.Tests/SceneRendering/SceneRendererTests.cs, test/DemaConsulting.CanvasNet.Render3D.Tests/SceneRendering/SceneRendererCsgTests.cs, test/DemaConsulting.CanvasNet.Render3D.Tests/SceneRendering/SceneRendererTransparencyTests.cs, test/DemaConsulting.CanvasNet.Render3D.Tests/SceneRendering/CsgOperandValidatorTests.cs, test/DemaConsulting.CanvasNet.Render3D.Tests/SceneRendering/SceneRenderOptionsTests.cs, test/DemaConsulting.CanvasNet.Render3D.Tests/SceneRendering/SceneRenderDiagnosticsTests.cs, test/DemaConsulting.CanvasNet.Render3D.Tests/SceneRendering/TileBinnerTests.cs, test/DemaConsulting.CanvasNet.Render3D.Tests/SceneRendering/SampleResolverTests.cs */
        comment designRef /* Design: docs/design/canvas-net-render3d/scene-rendering/scene-renderer.md */
        comment verificationRef /* Verification: docs/verification/canvas-net-render3d/scene-rendering/scene-renderer.md */
        comment reqRef /* Requirements: docs/reqstream/canvas-net-render3d/scene-rendering/scene-renderer.yaml */
    }
}
