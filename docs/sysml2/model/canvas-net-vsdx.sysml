package CanvasNet {
    part def CanvasNetVsdxSystem {
        doc /* CanvasNetVsdx is a Microsoft Visio (.vsdx) diagram-rendering system, distributed as the separate DemaConsulting.CanvasNet.Vsdx NuGet package. Unlike CanvasNetPptx's own incrementally-delivered phase history, CanvasNetVsdx ships its complete, final feature set as a single pull request, described here in full: an OPC (Open Packaging Conventions) package layer opening a .vsdx file as a read-only ZipArchive and resolving [Content_Types].xml plus the _rels/.rels -> visio/document.xml -> masters.xml/pages.xml/theme1.xml relationship chain (including per-page and per-master .rels indirection); a page/shape model parsing visio/pages/pages.xml's page index (PageWidth/PageHeight) and each pageN.xml's <Shapes>/<Shape> tree; shape geometry and transform resolution implementing the VisioML geometry row vocabulary (MoveTo/LineTo/RelMoveTo/RelLineTo resolved into path segments, EllipticalArcTo/ArcTo converted into an ArcTo path command reaching the row's own destination point - with a zero-bow ArcTo row degrading to a plain LineTo - and NURBSTo/InfiniteLine and any other unrecognized row type tolerantly skipped rather than approximated) and the shape-local-to-page affine transform (including the 1-D begin/end-derived transform special case used by connectors); Master/MasterShape cell-and-geometry-row inheritance (an instance cell with F="Inh" or no cell at all falls through to the master's resolved value; a geometry row is matched and merged, or marked deleted, by IX); the StyleSheet chain resolution for LineStyle/FillStyle/TextStyle (including direct per-shape overrides and the built-in 24-color Visio palette; no document-level <Colors>/<FaceNames> extension table is parsed); text rendering (<Text> run parsing against Section N="Character"/"Paragraph" rows, the implicit text-box-equals-shape-box default, and connector text positioning); connector/glue-point routing (<Connects> parsing and the static glue-point resolution algorithm, trusting Visio's own pre-baked BeginX/Y/EndX/Y values, plus arrowhead rendering); color/fill resolution (explicit hex and built-in-palette-index colors, solid fill only - every non-solid FillPattern value degrades to solid fill rather than a gradient/hatch approximation - and best-effort Themed-cell resolution against an optional theme1.xml); and arbitrarily nested group/child-shape handling (a child's PinX/PinY/.../Angle cells are expressed directly in the parent group's own local box, with no separate chOff/chExt-style remap step required). Embedded images/Foreign shapes, non-trivial Themed theme-variation resolution, non-solid FillPattern hatch/gradient combinations beyond solid, the full BeginArrow/EndArrow style-index table, and the RelCubBezTo/SplineStart/SplineKnot/PolylineTo/Ellipse geometry row types remain explicitly deferred, each a documented gap in the format research underlying this design - see docs/design/canvas-net-vsdx.md's own Design Constraints section for the complete deferred-feature boundary and the Implementation Phase Plan this system's delivery follows. */

        comment testRef /* Test: test/DemaConsulting.CanvasNet.Vsdx.Tests/VsdxSystemIntegrationTests.cs */
        comment designRef /* Design: docs/design/canvas-net-vsdx.md */
        comment verificationRef /* Verification: docs/verification/canvas-net-vsdx.md */
        comment reqRef /* Requirements: docs/reqstream/canvas-net-vsdx.yaml */
        comment /* CanvasNetVsdx depends on the sibling CanvasNet system (referenced via a ProjectReference from its own csproj, matching the architecture convention every package-bounded system in this repository follows) - specifically its Canvas (Surface/Rgba32), Geometry (Path/PathBuilder/Rect), Drawing (PathFiller/PathStroker), and Fonts (TrueTypeFont/SystemFontCatalog) subsystems. No Drawing.Gradient type is referenced: every non-solid FillPattern value degrades to solid fill (see the Design Constraints section of docs/design/canvas-net-vsdx.md). The Codecs subsystem is reserved for the deferred embedded-image/Foreign-shape capability and is not yet used. CanvasNetVsdx must never reference CanvasNetPptx, CanvasNetPdf, or CanvasNetCharts: no construct analogous to a PPTX <p:graphicFrame> chart reference was found in the format research underlying this design, so (unlike CanvasNetPptx) CanvasNetVsdx has no CanvasNetCharts dependency at all. A future, explicitly out-of-scope dependency on the sibling CanvasNetSvg system (to rasterize an embedded SVG foreign object, mirroring CanvasNetPptx's own "Phase 2 Follow-Up: SVG-Only Picture Blip Rendering") is anticipated but not yet modeled - see docs/design/canvas-net-svg.md's own Dependencies section, which already names CanvasNetVsdx as a future, one-directional consumer. */

        part vsdxDocument : VsdxDocument;

        dependency usesCanvas from CanvasNetVsdxSystem to Canvas;
        dependency usesGeometry from CanvasNetVsdxSystem to Geometry;
        dependency usesDrawing from CanvasNetVsdxSystem to Drawing;
        dependency usesFonts from CanvasNetVsdxSystem to Fonts;
        dependency usesPackaging from CanvasNetVsdxSystem to Packaging;
        dependency usesRendering from CanvasNetVsdxSystem to Rendering;
        dependency usesImageSources from CanvasNetVsdxSystem to ImageSources;
    }
}
