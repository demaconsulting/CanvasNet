package CanvasNet {
    /* cspell:ignore xfrm prst cust bodyPr pPr rPr txBody txStyles lstStyle defRPr normAutofit noAutofit spAutoFit lnSpcReduction fontScale */
    /* cspell:ignore srcRect blipFill tblGrid gridCol tcPr hMerge vMerge gridSpan rowSpan grpSp grpSpPr cxnSp graphicFrame pattFill spTree */
    /* cspell:ignore tblStyle wholeTbl tcStyle tcBdr insideH insideV bandRow firstRow band1H band2H */
    part def PptxDocument {
        doc /* OOXML (Office Open XML) package parser and presentation-rendering codec, delivered incrementally across Phases 1a-1f, each additive to the last. Phase 1a implements the package layer: opens a .pptx file as a read-only ZipArchive, resolves [Content_Types].xml's default extension mappings and part-specific overrides, and resolves package-level (_rels/.rels) and per-part relationships (including relative-target resolution with ".." traversal). Phase 1b adds the presentation/theme/master/layout/slide model: parses ppt/presentation.xml's declared slide size and ordered slide list, resolves each slide master's theme (color/font scheme), structurally parses each master/layout/slide's placeholder shapes, and implements the verified ECMA-376 placeholder property-inheritance resolver (slide -> layout matched by idx alone, layout -> master matched by type alone via a fixed remapping table). Phase 1c adds DrawingML shape geometry and paint resolution: a shape's <a:xfrm> position/rotation/flip transform, a <p:grpSp> group's chOff/chExt child-coordinate-space transform composition, <a:prstGeom> preset geometry (28 supported names, including a later-hardening-pass-added curved-arrow family) and <a:custGeom> custom path-command parsing resolved into the core Path type, and <a:solidFill>/<a:gradFill>/<a:noFill> fill plus <a:ln> stroke resolution into core paint types - including scheme-color lookup through the resolved theme, the lumMod/lumOff/shade/tint/alpha color-transform pipeline, and a stroked outline realized via the core PathStroker. Phase 1d adds DrawingML text body parsing (<p:txBody>/<a:bodyPr>/<a:p>/<a:pPr>/<a:r>/<a:rPr>/<a:t>), attribute-level run/paragraph property inheritance through the placeholder/layout/master (including the master's own <p:txStyles> titleStyle/bodyStyle/otherStyle buckets)/theme chain, word-wrap/alignment/vertical-anchor/autofit text layout, and glyph-ink rendering onto a core Surface via the core Fonts.TrueTypeFont/SystemFontCatalog and Drawing.PathFiller, mirroring the PDF renderer's own glyph-painting pattern. Phase 1e adds dedicated <p:pic> picture-shape support (content-type dispatch mirroring CanvasNetSvg's SvgCodec.ResolveRasterDecoder, <a:srcRect> crop-rectangle resolution, and y-down resampled compositing (SurfaceResampler single-pass device resampling, area averaging when shrunk and Catmull-Rom bicubic otherwise, with an inverse-mapped fallback for rotated placements) that deliberately omits the PDF renderer's own y-up vertical flip), <a:tbl> table support (structure/cell parsing reusing the Phase 1c/1d fill/border/text-body resolvers verbatim, merge-aware cell-rect resolution, and cell fill/border/text painting), and recursive, full shape-tree parsing across a slide's own <p:sp>/<p:pic>/<p:graphicFrame>/<p:grpSp> elements (including nested <p:grpSp> child-transform composition) with lazy, invoke-on-demand theme resolution so a shape tree with no <p:graphicFrame> never resolves a theme at all. Phase 1f adds the public, slide-level rendering API: PptxDocument.Render(int slideIndex, int width, int height, PptxRenderOptions? options) and a DPI convenience overload, which walk a slide's full PptxSlide.ShapeTree recursively in document order with an accumulating transform, dispatching each node kind to the already-verified Phase 1c/1d/1e resolvers/painters verbatim - composing a group's own already-resolved child transform, resolving an ordinary/placeholder shape's geometry/fill/stroke/text (a placeholder's own text is always read from the slide-level shape's own txBody, never from its matched layout placeholder), compositing a picture's embedded image, and painting a graphic frame's own table - clearing the destination Surface to PptxRenderOptions.BackgroundColor (default opaque white) before painting, and silently skipping a shape/picture/graphic-frame with no resolvable xfrm or a picture with no blipFill, mirroring ParseShapeTree's own tolerant-tree-walk precedent. With Phase 1f, the planned PPTX 1.0 feature set was complete. A Phase 2 Follow-Up pass then closed the single highest-visual-impact gap left by Phase 1f: a slide's own <p:cSld>/<p:bg> background fill is now resolved - falling back to its layout's, then its master's, own <p:bg> when the slide declares none, then to PptxRenderOptions.BackgroundColor only when none of the three declare one at all - and painted across the full slide before the shape-tree walk, reusing the existing Phase 1c ResolveFill/ResolveColor pipeline verbatim (including a new, optional phClr-override parameter threaded through it for <p:bgRef> theme-indexed resolution against a new PptxTheme.BgFillStyleList, parsed from <a:fmtScheme>/<a:bgFillStyleLst>). Solid-color fills and theme-indexed <p:bgRef> fills are fully supported; a linear gradient background fill is best-effort (inheriting Phase 1c's own linear-only boundary unchanged); a pattern or picture background fill remains explicitly deferred (inheriting ResolveFill's own pre-existing PptxUnsupportedFeatureException boundary unchanged). A non-placeholder shape's own background fill via <a:blipFill>/<a:pattFill> inside <p:spPr> (picture/pattern fill remains scoped to a dedicated <p:pic> shape's own <p:blipFill>), picture effects/shadows, nested tables, table auto-sizing to fit overflowing cell content (each row's resolved height is taken verbatim from its declared <a:tr h="..."> value, with no growth to accommodate overflowing cell content), table style/banding (<a:tableStyleId>), <p:cxnSp> connector shapes, group-level style cascading beyond transform composition, radial/path gradients, <a:avLst> adjustment-value parsing, bullets/numbering, full text justification, <a:spAutoFit> shape-resize autofit, kerning, and text clipping on overflow remain out of scope; none of these is a currently planned phase, and any of them remaining important is a candidate for a future, corpus-driven hardening pass (pptx-phase-2), not a scheduled increment. A further Phase 2 Follow-Up pass then closed the master/layout decorative-shape gap: a slide's own master and layout each contribute their own full shape tree - rendered beneath the slide's own shape tree, in master-then-layout-then-slide order, with each matched placeholder shape skipped (a placeholder's own geometry/fill/stroke/text is painted exactly once, from the slide-level shape, via the existing placeholder-inheritance resolver) so only genuine, non-placeholder decorative shapes contributed by the master/layout are painted - reusing the existing Phase 1c-1e geometry/paint/text/picture/table resolvers verbatim. A further Phase 2 Follow-Up pass closed the bullets/numbering gap: a paragraph's <a:buChar> character, <a:buAutoNum> auto-number marker, or explicit <a:buNone> absence is now parsed and resolved through the same four-tier placeholder/layout/master inheritance chain established for other paragraph properties, formatted into its rendered string for the eleven most common Latin-numeral auto-number schemes, and measured and painted at the paragraph's own gutter without ever overlapping its text. A further Phase 2 Follow-Up pass closed the <p:cxnSp> connector-shapes gap: a <p:cxnSp> is now parsed into its own shape-tree node alongside every other shape kind, and the public rendering API paints its resolved straight/elbow/curved line - merging its own line style with its style-reference fallback - and orients an optional stroked or filled arrowhead at either end; an unrecognized connector preset degrades to that one connector being invisible rather than aborting the slide. A subsequent regression fix corrected two real-file rendering failures this pass introduced: a master/layout decorative shape (including one nested inside a group) that itself throws PptxUnsupportedFeatureException while painting is now caught and only that single shape is skipped, so one already-deferred feature (for example an EMF picture) no longer aborts rendering for the rest of the slide - a slide's own shape still hard-fails unchanged; and a <a:blip> declaring only a Microsoft SVG extension fallback (<a:extLst>/<a:ext uri="{96DAC541-7B7A-43D3-8B79-37D633B846F1}">, the "Insert Icon" SVG-with-no-raster-fallback pattern) is now correctly classified as PptxUnsupportedFeatureException (feature token "pptx-image-svg-only") rather than misclassified as a malformed-data InvalidDataException. A further Phase 2 Follow-Up pass replaced that same "pptx-image-svg-only" PptxUnsupportedFeatureException with a successful decode: the Microsoft SVG extension's own <asvg:svgBlip r:embed="..."> relationship is now resolved (scoped to the owning part, exactly like a normal raster r:embed) and its referenced .svg media part is rasterized via the sibling CanvasNetSvg package's SvgCodec - using SvgCodec.GetInfo to measure the SVG's own intrinsic viewBox/width/height (clamped to [1, Surface.MaxDimension] on each axis) and SvgCodec.Load to rasterize at that resolution - returning the decoded Surface from ResolvePictureSurface exactly like any other raster image, so every downstream consumer (crop/srcRect, stretch/tile, shape transform, master/layout painting, disposal/ownership tracking) is unchanged; only the same extension present but with no r:embed of its own still throws InvalidDataException, and a malformed/unparsable referenced SVG still propagates SvgCodec's own InvalidDataException unchanged. A further bug fix corrected a real-world-verified compositing defect confirmed against a user-supplied deck: Phase 1e's own picture compositing loop previously overwrote each destination pixel outright with the raw sampled source pixel, ignoring the source image's own alpha channel entirely, so a PNG logo with genuine RGBA transparency rendered with a solid, incorrect matte rectangle instead of showing the slide background through its transparent area; the loop now alpha-blends each sampled source pixel over the existing destination pixel using the standard Porter-Duff "over" formula, via the public, single-pixel core Rgba32.CompositeOver(Rgba32, Rgba32) helper shared with (and formula-identical to) CanvasNetPdf's own CompositeImageOntoSurface fix for the same defect. A further Phase 2 Follow-Up pass fixed a color-map-indirection defect: bg1/tx1/bg2/tx2 scheme-color resolution previously hard-coded a fixed bg1->Light1/tx1->Dark1/bg2->Light2/tx2->Dark2 mapping, ignoring the slide master's own required <p:clrMap> and any layout/slide <p:clrMapOvr> override; these four aliases now correctly indirect through the effective, per-slide color map (slide <p:clrMapOvr> overriding layout <p:clrMapOvr> overriding the master's own <p:clrMap>, with an <a:masterClrMapping/> marker at any tier falling through to the next) before the existing theme-slot lookup, closing the gap for any non-identity (for example dark/inverted) master or layout. A further bug fix corrected ResolveLineStyle's own stroke-width resolution: a genuinely-absent <a:ln> w attribute previously collapsed to the same "no stroke" outcome as an explicit w="0", so a real-world <a:ln> that declares only a color (relying on PowerPoint's own default stroke weight) rendered with no visible outline at all; a genuinely-absent w now resolves to PowerPoint's own observed default stroke width (9525 EMU / 0.75pt, an application-level convention rather than a formal XSD schema default), while an explicitly-present w="0" or negative w still resolves to no stroke exactly as before - scoped narrowly to ResolveLineStyle itself, leaving ResolveShapeLineStyle's and ResolveConnectorLineStyle's own separate width-merge logic unchanged. A further bug fix corrected a bullet-gutter/text-start-X collision confirmed against a real-world buAutoNum paragraph (marL="320040", lvl="1", no indent attribute, no placeholder/master tier contributing one): PositionLines now clamps a bulleted first line's own text-start-X to never fall short of the bullet glyph's own gutter position plus its own measured width, so the bullet and the paragraph's own text never paint at an overlapping X coordinate, regardless of the paragraph's resolved indent. A further bug fix corrected an underline-rendering defect confirmed against a real-world corpus fixture: a text run's resolved <a:rPr u="sng"/> (and every other ECMA-376 underline-style value) was parsed into an effective property that nothing downstream ever consumed, so an explicitly-authored underline rendered with no underline at all; underline style/color now resolve through the same four-tier inheritance chain as every other text property, and PositionLines/PaintTextLayout now emit and paint a per-run underline span - continuous across a run's own interior whitespace but never bridging a run boundary, with thickness/offset approximated proportional to the run's own font size - closing the gap. A further Phase 2 Follow-Up pass closed the table-style/banding gap: a new PptxDocument.TableStyles.cs resolves a <a:tbl>/<a:tblPr>'s <a:tableStyleId> against the presentation package's own ppt/tableStyles.xml part (tolerating every "not found" cause by falling back to today's plain, style-less cell rendering without throwing) and applies the matched <a:tblStyle>'s <a:wholeTbl> base tier to every cell, its <a:band1H>/<a:band2H> tiers alternating by non-header row parity when <a:tblPr bandRow="1"> (a tier missing its own fill falling through to the next lower tier rather than to "no fill"), and its <a:firstRow> tier overriding both for the header row when <a:tblPr firstRow="1">, with a cell's own explicit <a:tcPr> fill/border always taking final precedence over every style tier - mirroring ResolveShapeLineStyle's own established "explicit always wins" precedence pattern and reusing the existing ResolveFill/ResolveLineStyle resolvers verbatim for every style-tier color, including schemeClr. firstCol/lastCol/lastRow/corner-cell style parts, column banding (band1V/band2V), and table-style-driven font color remain explicitly deferred. A further Phase 2 Follow-Up pass closed the default-tab-stop-expansion gap confirmed against a real-world corpus slide (literal digit-plus-tab-plus-sentence "numbered list" paragraphs, not buAutoNum bullets): a literal U+0009 TAB run character previously measured via the shared ResolveGlyph font-glyph lookup (resolving to a near-zero .notdef advance for most fonts' own missing cmap entry) now expands to the next default 914400-EMU (1 inch) tab stop instead, isolated as its own single-character token and computed dynamically from the running cursor position for both the word-wrap fit decision and the rendered cursor expansion; explicit <a:tabLst> tab-stop support remains out of scope, since no corpus slide declares one. A further Phase 2 Follow-Up pass closed the table-row-height-growth gap: ResolveCellRects now optionally grows a row's own effective height past its stored <a:tr h="..."> value to fit its tallest single-row cell's own wrapped text, computed via a new MeasureRequiredTextHeightEmu entry point built atop a verbatim extraction (ResolveWrappedLines) of ResolveTextLayout's own pre-existing word-wrap/autofit steps, measured against an unbounded height sentinel so the measurement can never itself trigger autofit shrinkage; a row-spanning cell's own shortfall against its spanned rows' stored height sum is added entirely onto its last spanned row; omitting the new optional theme/fontResolver parameters preserves today's stored-height-only behavior unconditionally, so every pre-existing caller is unaffected and only PaintTable's own production call site opts in. A further Phase 2 Follow-Up pass closed the slide-number-field gap: an <a:fld type="slidenum"> field is now parsed alongside plain <a:r> runs (its cached <a:t> text captured but not trusted, since PowerPoint caches a stale value at authoring time), and PptxDocument.Render's slide-level entry point substitutes every such field's text with the shape's own actual one-based slide index immediately before painting (SubstituteSlideNumberField), per slide, so a rendered deck always shows the slide's true current number rather than whatever number PowerPoint happened to cache; every other <a:fld> type (for example "datetime1") is left at its cached text unchanged. A non-placeholder shape's own txBody lstStyle level properties are honored ahead of the master's otherStyle (a master date/slide-number text box keeps its 12pt size). A further Phase 2 Follow-Up pass made a slide's own EMF/WMF <p:pic> picture (feature token "pptx-image-metafile") tolerated rather than fatal: by default Render skips just that picture (nothing drawn; EMF/WMF rendering remains a known gap) and reports it through the optional PptxRenderOptions.OnUnsupportedPictureSkipped callback, while PptxRenderOptions.StrictUnsupportedPictures = true keeps throwing PptxUnsupportedFeatureException. The unit also covers PptxImageSource (the IImageSource for .pptx files: the slide the fragment of the link names with slide=N or page=N, else the first, fitted inside the placement over a transparent background, skipped pictures reported) for the shared image resolver of the core ImageSources subsystem. */

        comment sourceRef /* Source: src/DemaConsulting.CanvasNet.Pptx/PptxImageSource.cs, src/DemaConsulting.CanvasNet.Pptx/PptxDocument.cs, src/DemaConsulting.CanvasNet.Pptx/PptxDocument.Package.cs, src/DemaConsulting.CanvasNet.Pptx/NamespaceDoc.cs, src/DemaConsulting.CanvasNet.Pptx/PptxDocument.Presentation.cs, src/DemaConsulting.CanvasNet.Pptx/PptxSlideSize.cs, src/DemaConsulting.CanvasNet.Pptx/PptxDocument.Theme.cs, src/DemaConsulting.CanvasNet.Pptx/PptxTheme.cs, src/DemaConsulting.CanvasNet.Pptx/PptxDocument.Masters.cs, src/DemaConsulting.CanvasNet.Pptx/PptxDocument.Layouts.cs, src/DemaConsulting.CanvasNet.Pptx/PptxDocument.Slides.cs, src/DemaConsulting.CanvasNet.Pptx/PptxPlaceholder.cs, src/DemaConsulting.CanvasNet.Pptx/PptxDocument.Inheritance.cs, src/DemaConsulting.CanvasNet.Pptx/PptxPlaceholderProperties.cs, src/DemaConsulting.CanvasNet.Pptx/PptxDocument.Geometry.cs, src/DemaConsulting.CanvasNet.Pptx/PptxDocument.Paint.cs, src/DemaConsulting.CanvasNet.Pptx/PptxPresetGeometry.cs, src/DemaConsulting.CanvasNet.Pptx/PptxShapeFrame.cs, src/DemaConsulting.CanvasNet.Pptx/PptxPaint.cs, src/DemaConsulting.CanvasNet.Pptx/PptxLineStyle.cs, src/DemaConsulting.CanvasNet.Pptx/PptxUnsupportedFeatureException.cs, src/DemaConsulting.CanvasNet.Pptx/PptxTextBody.cs, src/DemaConsulting.CanvasNet.Pptx/PptxDocument.Text.cs, src/DemaConsulting.CanvasNet.Pptx/PptxEffectiveTextProperties.cs, src/DemaConsulting.CanvasNet.Pptx/PptxDocument.TextInheritance.cs, src/DemaConsulting.CanvasNet.Pptx/PptxTextLayout.cs, src/DemaConsulting.CanvasNet.Pptx/PptxDocument.TextLayout.cs, src/DemaConsulting.CanvasNet.Pptx/PptxDocument.TextRender.cs, src/DemaConsulting.CanvasNet.Pptx/PptxPicture.cs, src/DemaConsulting.CanvasNet.Pptx/PptxDocument.Images.cs, src/DemaConsulting.CanvasNet.Pptx/PptxTable.cs, src/DemaConsulting.CanvasNet.Pptx/PptxDocument.Tables.cs, src/DemaConsulting.CanvasNet.Pptx/PptxDocument.TableStyles.cs, src/DemaConsulting.CanvasNet.Pptx/PptxShapeTree.cs, src/DemaConsulting.CanvasNet.Pptx/PptxDocument.ShapeTree.cs, src/DemaConsulting.CanvasNet.Pptx/PptxRenderOptions.cs, src/DemaConsulting.CanvasNet.Pptx/PptxDocument.Render.cs, src/DemaConsulting.CanvasNet.Pptx/PptxDocument.Background.cs */
        comment testRef /* Test: test/DemaConsulting.CanvasNet.Pptx.Tests/PptxImageSourceTests.cs, test/DemaConsulting.CanvasNet.Pptx.Tests/PptxDocumentTests.cs, test/DemaConsulting.CanvasNet.Pptx.Tests/PptxSystemIntegrationTests.cs, test/DemaConsulting.CanvasNet.Pptx.Tests/PptxGeometryTests.cs, test/DemaConsulting.CanvasNet.Pptx.Tests/PptxPaintTests.cs, test/DemaConsulting.CanvasNet.Pptx.Tests/PptxTextTests.cs, test/DemaConsulting.CanvasNet.Pptx.Tests/PptxTextLayoutTests.cs, test/DemaConsulting.CanvasNet.Pptx.Tests/PptxTextRenderTests.cs, test/DemaConsulting.CanvasNet.Pptx.Tests/PptxImagesTests.cs, test/DemaConsulting.CanvasNet.Pptx.Tests/PptxTablesTests.cs, test/DemaConsulting.CanvasNet.Pptx.Tests/PptxGroupsTests.cs, test/DemaConsulting.CanvasNet.Pptx.Tests/PptxRenderTests.cs, test/DemaConsulting.CanvasNet.Pptx.Tests/PptxBackgroundTests.cs, test/DemaConsulting.CanvasNet.Pptx.Tests/PptxFixturesCorpusTests.cs, test/DemaConsulting.CanvasNet.Pptx.Tests/PptxColorMapTests.cs */
        comment designRef /* Design: docs/design/canvas-net-pptx/pptx-document.md */
        comment verificationRef /* Verification: docs/verification/canvas-net-pptx/pptx-document.md */
        comment reqRef /* Requirements: docs/reqstream/canvas-net-pptx/pptx-document.yaml */
    }
}
