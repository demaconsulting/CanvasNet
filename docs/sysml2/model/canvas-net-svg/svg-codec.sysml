package CanvasNet {
    part def SvgCodec {
        doc /* Decode/rasterize-only loader for a common real-world subset of SVG documents, rasterizing them into Surface pixel buffers. The codec itself performs no file or network I/O: an image element's external href is loaded only through the explicit, opt-in SvgLoadOptions.ImageResolver (an IImageResolver of the core ImageSources subsystem), whose calls are charged against the shared work budget and whose pictures are never cached; a data URI is decoded by the codec itself. Every SVG length accepts CSS units (px, pt, pc, in, cm, mm, Q, em, ex, ch, rem, lh, rlh, vw, vh, vmin, vmax), percentages and calc()/min()/max()/clamp(), resolved to user units by one shared resolver (SvgCodec.Lengths.cs) under a three-class malformed-value policy (strict for geometry, tolerant for the root size and paint servers, ignored for font properties); font-size, line-height and the font shorthand are resolved in SvgCodec.FontSize.cs. The SvgImageSource unit-level class is the IImageSource for .svg files: it draws a linked SVG file at the size of its placement over a transparent background and resolves that file's own images through the scoped resolver of the request. An internal (non-public) RenderDiagnostics/LoadWithDiagnostics seam lets tests observe rendering decisions without changing the public API. */

        comment sourceRef /* Source: src/DemaConsulting.CanvasNet.Svg/SvgCodec.cs, src/DemaConsulting.CanvasNet.Svg/SvgCodec.Core.cs, src/DemaConsulting.CanvasNet.Svg/SvgCodec.Parsing.cs, src/DemaConsulting.CanvasNet.Svg/SvgCodec.Elements.cs, src/DemaConsulting.CanvasNet.Svg/SvgCodec.Shapes.cs, src/DemaConsulting.CanvasNet.Svg/SvgCodec.PathData.cs, src/DemaConsulting.CanvasNet.Svg/SvgCodec.PathRender.cs, src/DemaConsulting.CanvasNet.Svg/SvgCodec.Filters.cs, src/DemaConsulting.CanvasNet.Svg/SvgCodec.Filters.ColorMatrix.cs, src/DemaConsulting.CanvasNet.Svg/SvgCodec.Filters.ComponentTransfer.cs, src/DemaConsulting.CanvasNet.Svg/SvgCodec.Filters.Morphology.cs, src/DemaConsulting.CanvasNet.Svg/SvgCodec.Filters.Convolution.cs, src/DemaConsulting.CanvasNet.Svg/SvgCodec.Filters.DisplacementMap.cs, src/DemaConsulting.CanvasNet.Svg/SvgCodec.Filters.Tile.cs, src/DemaConsulting.CanvasNet.Svg/SvgCodec.Filters.DropShadow.cs, src/DemaConsulting.CanvasNet.Svg/SvgCodec.Filters.FeImage.cs, src/DemaConsulting.CanvasNet.Svg/SvgCodec.Paint.cs, src/DemaConsulting.CanvasNet.Svg/SvgCodec.Gradients.cs, src/DemaConsulting.CanvasNet.Svg/SvgCodec.Markers.cs, src/DemaConsulting.CanvasNet.Svg/SvgCodec.Text.cs, src/DemaConsulting.CanvasNet.Svg/SvgCodec.Attributes.cs, src/DemaConsulting.CanvasNet.Svg/SvgCodec.Lengths.cs, src/DemaConsulting.CanvasNet.Svg/SvgCodec.FontSize.cs, src/DemaConsulting.CanvasNet.Svg/SvgFontFace.cs, src/DemaConsulting.CanvasNet.Svg/SvgFontStyle.cs, src/DemaConsulting.CanvasNet.Svg/SvgLoadOptions.cs, src/DemaConsulting.CanvasNet.Svg/SvgImageSource.cs, src/DemaConsulting.CanvasNet.Svg/SvgCodec.Fonts.cs, src/DemaConsulting.CanvasNet.Svg/SvgCodec.ClippingAndMasking.cs, src/DemaConsulting.CanvasNet.Svg/SvgCodec.Patterns.cs, src/DemaConsulting.CanvasNet.Svg/SvgCodec.PreserveAspectRatio.cs, src/DemaConsulting.CanvasNet.Svg/SvgCodec.Image.cs, src/DemaConsulting.CanvasNet.Svg/SvgCodec.Filters.Lighting.cs, src/DemaConsulting.CanvasNet.Svg/SvgCodec.Filters.Turbulence.cs, src/DemaConsulting.CanvasNet.Svg/SvgCodec.Filters.Blend.cs, src/DemaConsulting.CanvasNet.Svg/SvgCodec.Css.Parser.cs, src/DemaConsulting.CanvasNet.Svg/SvgCodec.Css.Selectors.cs, src/DemaConsulting.CanvasNet.Svg/SvgCodec.Css.Cascade.cs, src/DemaConsulting.CanvasNet/Codecs/ImageInfo.cs (cross-package: shared header-only probe result type in the core DemaConsulting.CanvasNet package) */
        comment testRef /* Test: test/DemaConsulting.CanvasNet.Svg.Tests/SvgCodecTests.cs, test/DemaConsulting.CanvasNet.Svg.Tests/SvgFixtureTests.cs, test/DemaConsulting.CanvasNet.Svg.Tests/SvgSystemIntegrationTests.cs, test/DemaConsulting.CanvasNet.Svg.Tests/SvgImageResamplingTests.cs, test/DemaConsulting.CanvasNet.Svg.Tests/SvgImageResolverTests.cs, test/DemaConsulting.CanvasNet.Svg.Tests/SvgImageSourceTests.cs, test/DemaConsulting.CanvasNet.Svg.Tests/SvgPatternTileSmoothingTests.cs, test/DemaConsulting.CanvasNet.Svg.Tests/SvgDefaultFontTests.cs, test/DemaConsulting.CanvasNet.Svg.Tests/SvgLengthUnitTests.cs, test/DemaConsulting.CanvasNet.Svg.Tests/SvgFontSizeTests.cs, test/DemaConsulting.CanvasNet.Svg.Tests/SvgLengthTestSupport.cs */
        comment designRef /* Design: docs/design/canvas-net-svg/svg-codec.md */
        comment verificationRef /* Verification: docs/verification/canvas-net-svg/svg-codec.md */
        comment reqRef /* Requirements: docs/reqstream/canvas-net-svg/svg-codec.yaml */
    }
}
