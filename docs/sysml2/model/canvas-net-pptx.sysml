package CanvasNet {
    part def CanvasNetPptxSystem {
        doc /* CanvasNetPptx is a PowerPoint (.pptx) presentation-rendering system, distributed as the separate DemaConsulting.CanvasNet.Pptx NuGet package. This feature was delivered incrementally across Phases 1a-1f, each additive to the last. Phase 1a implemented the underlying OOXML (Office Open XML) package layer: opening a .pptx file as a read-only ZipArchive, resolving [Content_Types].xml (default extension mappings and part-specific overrides), and resolving package-level (_rels/.rels) and per-part relationships, including relative-target resolution (for example "../slideLayouts/slideLayout1.xml"). Phase 1b added the presentation/theme/master/layout/slide model and the placeholder property-inheritance resolver: ppt/presentation.xml's declared slide size and ordered slide list, each slide master's theme (color/font scheme, resolved into DemaConsulting.CanvasNet.Canvas.Rgba32 values), structural placeholder-shape parsing for masters/layouts/slides, and the verified ECMA-376 placeholder matching algorithm. Phase 1c added DrawingML shape geometry and paint resolution: shape transform (position/rotation/flip, group child-coordinate-space composition), preset/custom geometry resolved into the core Geometry.Path type, and fill/stroke resolution into core Canvas paint types plus a stroked outline realized via the core Drawing.PathStroker. Phase 1d added DrawingML text body parsing, attribute-level run/paragraph property inheritance (including a slide master's own titleStyle/bodyStyle/otherStyle text-style buckets), word-wrap/alignment/vertical-anchor/autofit text layout, and glyph-ink rendering onto a core Canvas.Surface, resolving typefaces through the core Fonts subsystem and filling glyph outlines via the core Drawing.PathFiller. Phase 1e added dedicated <p:pic> picture-shape decoding/cropping/compositing (dispatching to the core Codecs subsystem), <a:tbl> table structure/cell-rect/paint resolution, and recursive, full <p:spTree> shape-tree parsing (including nested <p:grpSp> child-transform composition). Phase 1f added the public, slide-level Render API: a document-order walk of a slide's full shape tree dispatching each node to the already-verified Phase 1c/1d/1e resolvers and painters onto a Canvas.Surface, followed by subsequent Phase 2 Follow-Ups adding slide/layout/master <p:bg> background-fill resolution ahead of that walk, <a:buChar>/<a:buAutoNum> bullet/numbering rendering, and <p:cxnSp> connector-shape rendering. Subsequent Phase 2 Follow-Ups also closed the table-style/banding gap, the default-tab-stop-expansion gap, the table row-height-growth gap (a row now grows past its stored height to fit a cell's own wrapped text, instead of overlapping the next row), and the slide-number-field gap (an <a:fld type="slidenum"> field's cached, authoring-time text is now substituted with the shape's own actual slide index at render time instead of being trusted verbatim). Pattern/picture background fill, radial/path gradients, full group-shape rendering semantics beyond transform composition, full text justification, shape-resize autofit, kerning, text clipping on overflow, and nested tables remain explicitly deferred. */

        comment testRef /* Test: test/DemaConsulting.CanvasNet.Pptx.Tests/PptxSystemIntegrationTests.cs */
        comment designRef /* Design: docs/design/canvas-net-pptx.md */
        comment verificationRef /* Verification: docs/verification/canvas-net-pptx.md */
        comment reqRef /* Requirements: docs/reqstream/canvas-net-pptx.yaml */
        comment /* CanvasNetPptx depends on the sibling CanvasNet system (referenced via a ProjectReference from its own csproj, matching the architecture convention every package-bounded system in this repository follows). As of Phase 1b, CanvasNetPptx uses the Canvas subsystem's Rgba32 type to represent a theme's resolved color scheme. As of Phase 1c, CanvasNetPptx additionally uses the Geometry subsystem (Path/PathBuilder, to build and compose resolved shape geometry) and the Drawing subsystem (PathStroker/StrokeStyle, to realize a resolved stroke's outline). As of Phase 1d, CanvasNetPptx additionally uses the Fonts subsystem (TrueTypeFont/SystemFontCatalog, to resolve a DrawingML typeface name hint and extract glyph outlines) and the Drawing subsystem's PathFiller (to paint resolved glyph ink onto a Canvas.Surface). As of Phase 1e, CanvasNetPptx additionally uses the Codecs subsystem (PngCodec/JpegCodec/BmpCodec/TiffCodec/GifCodec, dispatched by content type in PptxDocument.Images.cs, to decode a <p:pic>'s embedded raster image) - each modeled below as a non-owning `dependency` relationship to the existing subsystem part def (not an ordinary `part` usage, which would incorrectly model it as an owned child of CanvasNetPptxSystem), mirroring CanvasNetPdf's and CanvasNetSvg's own precedent of adding a `dependency` edge only at the phase that actually first uses the referenced subsystem (for example CanvasNetPdf's Fonts dependency was added only at its own Phase 4, not at Phase 1). As of Phase 4, CanvasNetPptx additionally depends on the sibling CanvasNetCharts system (its own separate package, DemaConsulting.CanvasNet.Charts) - OpenXmlChartParser to parse a <p:graphicFrame>'s referenced chart#.xml OPC part into a Chart, and ChartRenderer to render that Chart before compositing it onto the slide surface - modeled below as a `dependency` edge to that sibling system's own part def (CanvasNetChartsSystem), not a `CanvasNet` subsystem; this dependency is strictly one-directional, since CanvasNetCharts must never reference CanvasNetPptx (see docs/design/canvas-net-charts.md's own Dependencies section). As of the Phase 2 Follow-Up "SVG-Only Picture Blip Rendering", CanvasNetPptx additionally depends on the sibling CanvasNetSvg system (its own separate package, DemaConsulting.CanvasNet.Svg) - SvgCodec.GetInfo/SvgCodec.Load to resolve a Microsoft "SVG-only" <p:pic> picture blip's (<a:extLst>/<a:ext uri="{96DAC541-7B7A-43D3-8B79-37D633B846F1}"> wrapping an <asvg:svgBlip r:embed="...">) own intrinsic size and rasterize it into a core Surface before compositing it via the existing PaintPicture primitive, exactly like any other decoded raster image - modeled below as a `dependency` edge to that sibling system's own part def (CanvasNetSvgSystem); this dependency is likewise strictly one-directional, since CanvasNetSvg must never reference CanvasNetPptx (see docs/design/canvas-net-svg.md's own Dependencies section). */

        part pptxDocument : PptxDocument;

        dependency usesCanvas from CanvasNetPptxSystem to Canvas;
        dependency usesGeometry from CanvasNetPptxSystem to Geometry;
        dependency usesDrawing from CanvasNetPptxSystem to Drawing;
        dependency usesFonts from CanvasNetPptxSystem to Fonts;
        dependency usesCodecs from CanvasNetPptxSystem to Codecs;
        dependency usesCharts from CanvasNetPptxSystem to CanvasNetChartsSystem;
        dependency usesSvg from CanvasNetPptxSystem to CanvasNetSvgSystem;
        dependency usesPackaging from CanvasNetPptxSystem to Packaging;
        dependency usesRendering from CanvasNetPptxSystem to Rendering;
        dependency usesImageSources from CanvasNetPptxSystem to ImageSources;
    }
}
