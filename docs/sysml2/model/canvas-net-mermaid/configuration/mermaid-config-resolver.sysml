package CanvasNet {
    part def MermaidConfigResolver {
        doc /* The internal static MermaidConfigResolver (partial class in four files) and the typed view of its result, MermaidConfig with FlowchartConfig, SequenceConfig, ClassConfig, StateConfig, ErConfig, PieConfig, GanttConfig, MindmapConfig, PacketConfig, GitGraphConfig, MermaidFontConfig, and ConfigScalar: Resolve computes the effective configuration of one measure or render call as Mermaid builds its current configuration. The layers, lowest first, are Mermaid's defaults with the default theme's variables, the theme option and the site configuration of MermaidRenderOptions (played as mermaid.initialize, a theme in the configuration winning over the option), the frontmatter config (with displayMode moved to gantt.displayMode), and the init and initialize directives in text order; a wrap directive sets wrap. The steps are literal ports of initialize, setSiteConfig, processFrontmatter, detectInit (a JSON error in any init directive ignores all of them; the config key of a single directive moves to the section of the diagram type), lodash merge, sanitizeDirective, addDirective, sanitize with the site's secure keys, updateCurrentConfig (the theme computed again only when the text names a theme), the flowchart init (the elk layout of an ELK flowchart and the copy of arrowMarkerAbsolute), and the layout step of the mindmap database's getData (the layout becomes cose-bilkent unless the user configuration sets one). Each layer is validated before the merge with located warnings: mermaid-config-secure-key for a secure key set by the text, mermaid-config-unknown-key for a key outside Mermaid's 705 configuration keys (with the nearest key as the hint, at most 32 hints), and mermaid-config-invalid for invalid directive JSON, arguments that are not an object, a frontmatter config that is not a mapping, a value of the wrong type (dropped, so the lower layer wins), a refused string, an unsupported theme (the newer neo and redux themes named as not supported), and a theme variable khroma cannot read (dropped and the theme computed again at most 16 times, else the theme without overrides). Directive JSON is limited to a depth of 64. MermaidConfig gives the theme, theme variables, fonts, look, layout, themeCSS, HTML labels, wrap, the flowchart section, the sequence section, the detector settings, and the location of the layer that set each top-level key. The sequence section has Mermaid's sequence defaults, typed sequence keys (font sizes and weights kept as a number or a text, as parseFontSize needs; the note and message alignments checked against the six that drawText honors), the fonts of the sequence renderer's setConf (a truthy top-level fontFamily, fontSize, or fontWeight replacing the section's), and the wrap rule of the sequence init (a true top-level wrap or a true sequence.wrap). The class section has Mermaid's effective class defaults (defaultRenderer, hideEmptyMembersBox, hierarchicalNamespaces, and padding unset) and the node spacing, rank spacing, and title margin that Mermaid's class renderer reads from the state section. The state and er sections have Mermaid's whole schema defaults and typed keys: the state default renderer (read by the detector settings), node spacing, rank spacing, and title margin, and the er diagram padding, entity padding, minimum entity width, node spacing, rank spacing, and title margin, a zero spacing falling back to its default and a zero title margin kept as the renderers read them. The pie and gantt sections have Mermaid's whole schema defaults and typed keys: the pie text position, donut hole, legend position, and highlighted slice, and the gantt title margin, bar height and gap, paddings, grid line start, font sizes, number of section styles, axis format, tick interval, top axis, display mode (also from the frontmatter displayMode), and width (useWidth). The mindmap section has the whole of Mermaid's schema defaults and typed keys: the padding (10), the maximum node width (200), the layout algorithm (cose-bilkent), and useMaxWidth. The packet section has the whole of Mermaid's schema defaults and typed keys: the row height, the bit width, and the bits per row (32), showBits (true), the paddings (5), and useMaxWidth, with the vertical padding grown by 10 when showBits is set, as the packet database's getConfig grows it. The gitGraph section has the whole of Mermaid's schema defaults and typed keys (eleven keys, nodeLabel and arrowMarkerAbsolute only type-checked) and typed access to the drawn settings: titleTopMargin (25), diagramPadding (8), mainBranchName (main), mainBranchOrder (0), showCommitLabel, showBranches, and rotateCommitLabel (true), parallelCommits (false), and useMaxWidth. The class is stateless; resolving with or without a sink gives the same configuration. */

        comment sourceRef /* Source: src/DemaConsulting.CanvasNet.Mermaid/Configuration/MermaidConfigResolver.cs, src/DemaConsulting.CanvasNet.Mermaid/Configuration/MermaidConfigResolver.Defaults.cs, src/DemaConsulting.CanvasNet.Mermaid/Configuration/MermaidConfigResolver.Merge.cs, src/DemaConsulting.CanvasNet.Mermaid/Configuration/MermaidConfigResolver.Validation.cs, src/DemaConsulting.CanvasNet.Mermaid/Configuration/MermaidConfig.cs */
        comment testRef /* Test: test/DemaConsulting.CanvasNet.Mermaid.Tests/Configuration/MermaidConfigResolverTests.cs, test/DemaConsulting.CanvasNet.Mermaid.Tests/Configuration/MermaidConfigResolverVectorTests.cs */
        comment designRef /* Design: docs/design/canvas-net-mermaid/configuration/mermaid-config-resolver.md */
        comment verificationRef /* Verification: docs/verification/canvas-net-mermaid/configuration/mermaid-config-resolver.md */
        comment reqRef /* Requirements: docs/reqstream/canvas-net-mermaid/configuration/mermaid-config-resolver.yaml */
    }
}
