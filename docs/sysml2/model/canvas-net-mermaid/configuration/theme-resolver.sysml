package CanvasNet {
    part def ThemeResolver {
        doc /* The internal static ThemeResolver (partial class in ThemeResolver.cs and one file per theme) with the JavaScript object model ThemeObject and Js, the flowchart style sheet FlowchartStyles with ShapePaint and TextPaint over the UnifiedStyles base of the diagrams drawn by the unified renderer (the selectors the Rendering units read) and the DiagramStyles base that holds the global rules shared by every style sheet (ThemeResolver.Styles.cs), the class, state, and ER style sheets ClassStyles, StateStyles, and ErStyles (ThemeResolver.DiagramStyles.cs), the sequence style sheet SequenceStyles with ShadowPaint (ThemeResolver.SequenceStyles.cs), the chart style sheets PieStyles with SlicePaint and GanttStyles with GanttElement and the packet style sheet PacketStyles (ThemeResolver.ChartStyles.cs), the mindmap style sheet MindmapStyles (ThemeResolver.MindmapStyles.cs), and the git graph style sheet GitGraphStyles with GitGraphElement and GitGraphComputedStyle (ThemeResolver.GitGraphStyles.cs). GetThemeVariables ports Mermaid's getThemeVariables for the five built-in themes default, base, dark, forest, and neutral: the constructor's base values, calculate (the default theme first resets every calculated placeholder), the overrides copied in, every color derived in updateColors in the class's own order with the khroma port ColorMath, and the overrides copied in again so that an overridden derived variable wins; overrides that are not an object are ignored. Every variable of every diagram type is computed, so the result equals Mermaid's object variable for variable. ThemeObject behaves as the JavaScript this of a theme class (undefined, the || and ?? fallbacks, member access, insertion order, and the JSON.stringify form). The color-scale loops that THEME_COLOR_LIMIT controls are capped at 64 iterations; a value that is not a color fails with a ColorFormatException that carries it, and an unsupported theme throws ArgumentException. The neo and redux themes of the pinned Mermaid are not ported. FlowchartStyles.Create builds the global rules of Mermaid's getStyles and the flowchart's styles.ts from the theme variables of a MermaidConfig as selector-keyed rules (only the declarations that change pixels, a declaration with an invalid value dropped as a browser drops it), appends the themeCSS rules of the flowchart's own selectors (an important theme declaration staying in effect) and reports every other themeCSS rule as mermaid-theme-css-unsupported, and resolves the paints of nodes, subgraphs, edges, markers, labels, the title, and the edge label background. SequenceStyles.Create builds the same global rules and the sequence rules of Mermaid's styles.js, appends the themeCSS rules of the sequence diagram's own selectors (reporting the others in the same way), and resolves the cascade over the attributes Mermaid gives each element, from least to most specific: shapes, lines (the line rule's 2 pixels, beaten by the message rules), text colors, shadows, boxes, and message lines, with typed paints for lifelines, frame lines, label boxes, markers, sequence numbers, and the drop shadows of boxes and menu panels (a CSS filter of none or one drop-shadow()). ClassStyles.Create builds the same global rules and the class rules of Mermaid's class styles.js, appends the themeCSS rules of the class diagram's own selectors (reporting the others), and resolves the paints of class boxes and dividers, namespaces, node, note, edge, and terminal labels, the edge label backgrounds, the relation markers, and the title in the root font. StateStyles.Create builds the global rules and the rules of Mermaid's state styles.js and resolves the state paint, the corner radii and cluster fills read by selector, the labels of states, transitions, notes, and composite titles (HTML and SVG titles in their own colors), the barb paint in the transition color, and the 18 pixel title; ErStyles.Create builds the global rules and the rules of Mermaid's ER styles.ts and resolves the entity paint, the 14 pixel edge labels and their one visible HTML background, the subgraph titles, the important marker paint that themeCSS cannot replace, and the title in the root font. PieStyles.Create builds the global rules and the rules of Mermaid's pieStyles.ts and resolves the slice paint over its section color (the opacity folded in, a highlighted slice opaque and 1.05 times larger), the outer circle, and the title, percentage, and legend fonts and colors. GanttStyles.Create builds the global rules and the rules of Mermaid's gantt styles.js and computes the style of an element from the classes of the element and its ancestors with a small class-set cascade (important declarations, then the specificity of compound and descendant selectors, then source order, over the presentation attributes), for the section rows, bars, milestones, task texts, section titles, grid, excluded days, today line, and title; themeCSS rules of the gantt selectors apply after them and others are reported as mermaid-theme-css-unsupported. MindmapStyles.Create builds the global rules and the rules of Mermaid's mindmap styles.ts for the classic look (the section fills, label colors, edge strokes, depth widths with the negative widths dropped, the line under a default node, the root's colors, and the gradient rule that makes that line 0 pixels wide in the themes with useGradient and mainBkg), appends the themeCSS rules of the mindmap selectors and of the .class element selectors of the classes of the diagram's nodes, and cascades the rules of a node's classes and shape element in sheet order (NodePaintFor and NodeLabelFor, which the other unified sheets answer with their one node rule). PacketStyles.Create builds the global rules and the six rules of Mermaid's packet styles.ts from the sheet's defaults merged with the theme variable packet (which replaces the dark and forest themes' object, each value written as JavaScript's String writes it), drops a font size that is a bare number as the browser does, appends the themeCSS rules of the packet selectors, and resolves the paint of a block (inheriting the root rule's paint where its own is dropped) and the fonts and colors of the labels, the first and last bit numbers, and the title. GitGraphStyles.Create builds the global rules and the rules of Mermaid's git styles.js for each of the THEME_COLOR_LIMIT colors (JavaScript's array length of the theme value, each color index taken modulo 8 for the named git colors), appends the themeCSS rules of the git graph selectors, gives the inline drop shadow of a branch label in the neo look, and computes the style of an element with a small CSS cascade (a rule over a presentation attribute, the matching rules ordered by the number of their classes and tags and then by their place in the sheet, the inline style over normal declarations, an important declaration over every normal one, inherited properties, and multiplied opacities), so that a commit id that is also a class of the sheet is styled by its rule, as in a browser. Every unified sheet gives the rendering whether it centers the SVG text of a node (CentersNodeSvgText: the flowchart and class sheets do, the state and ER sheets do not), the cluster title of an HTML or SVG title (ClusterTitle), and the root text (RootText); fade is shared by the sheets. The types are stateless or immutable. */

        comment sourceRef /* Source: src/DemaConsulting.CanvasNet.Mermaid/Configuration/ThemeResolver.cs, src/DemaConsulting.CanvasNet.Mermaid/Configuration/ThemeResolver.Default.cs, src/DemaConsulting.CanvasNet.Mermaid/Configuration/ThemeResolver.Base.cs, src/DemaConsulting.CanvasNet.Mermaid/Configuration/ThemeResolver.Dark.cs, src/DemaConsulting.CanvasNet.Mermaid/Configuration/ThemeResolver.Forest.cs, src/DemaConsulting.CanvasNet.Mermaid/Configuration/ThemeResolver.Neutral.cs, src/DemaConsulting.CanvasNet.Mermaid/Configuration/ThemeResolver.Styles.cs, src/DemaConsulting.CanvasNet.Mermaid/Configuration/ThemeResolver.SequenceStyles.cs, src/DemaConsulting.CanvasNet.Mermaid/Configuration/ThemeResolver.DiagramStyles.cs, src/DemaConsulting.CanvasNet.Mermaid/Configuration/ThemeResolver.ChartStyles.cs, src/DemaConsulting.CanvasNet.Mermaid/Configuration/ThemeResolver.MindmapStyles.cs, src/DemaConsulting.CanvasNet.Mermaid/Configuration/ThemeResolver.GitGraphStyles.cs */
        comment testRef /* Test: test/DemaConsulting.CanvasNet.Mermaid.Tests/Configuration/ThemeResolverTests.cs, test/DemaConsulting.CanvasNet.Mermaid.Tests/Fixtures/upstream-vectors/themes.json */
        comment designRef /* Design: docs/design/canvas-net-mermaid/configuration/theme-resolver.md */
        comment verificationRef /* Verification: docs/verification/canvas-net-mermaid/configuration/theme-resolver.md */
        comment reqRef /* Requirements: docs/reqstream/canvas-net-mermaid/configuration/theme-resolver.yaml */
    }
}
