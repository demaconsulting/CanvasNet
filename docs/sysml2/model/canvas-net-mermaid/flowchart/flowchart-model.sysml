package CanvasNet {
    part def FlowchartModel {
        doc /* The internal sealed FlowchartModel (a partial class in three files, implementing IMermaidDiagram) with its element types FlowVertex, FlowEdge, FlowSubgraph, FlowClass, FlowText, FlowLink, ShapeDataText, and DocumentItem: Mermaid's flowchart database (flowDb.ts) for one parsed text. The database operations that the parser calls keep Mermaid's semantics: the direction aliases, a vertex declared again merging into the first with its DOM id kept, labels sanitized as Mermaid's sanitizeText, shape data read as YAML for a vertex (checked lower-case shape names, labels, icons, images, asset sizes), an edge id (animation and curve), or a subgraph id (metadata, including the collapsed view), the link tokens of destructLink, edge ids L_start_end_n or the author's id once, classDef styles and text styles, class, linkStyle with default, interpolate, and shared style lists, click as the clickable class only, subgraph ids, titles, directions, and members, and the accessibility texts. What Mermaid's database fails on (a nameless subgraph, an unknown shape, a linkStyle index without an edge, invalid YAML) and the MaxEdges, MaxNodes (vertices and subgraphs), and MaxLabelLength (labels, titles, and accessibility texts) limits are located MermaidSyntaxExceptions at open. The model gives the document its metadata (no title of its own, the accessible title, the direction, and the counts with subgraph ids not counted as nodes); GetData maps it for each render to the LayoutData of the Rendering subsystem with that render's configuration (getTypeFromVertex shapes, compiled class styles, markers of destructEdgeType, curves and styles of linkStyle default, padding and spacings, inheritDir, collapsed subgraphs that hide their content and take over the crossing edges); ReportUnsupported reports, in order and located, a look other than classic, a layout other than dagre, node icons, and Font Awesome icons in labels; and Layout reports first, then draws the layout input through the ClusterLayout with the node image loader, the label builder, the flowchart style sheet, and the layout work meter of the render, places the frontmatter title as insertTitle does, and returns a Scene whose view box is the drawn bounds grown by the diagram padding. Once parsing is over the model is never changed and is safe for concurrent use. */

        comment sourceRef /* Source: src/DemaConsulting.CanvasNet.Mermaid/Flowchart/FlowchartModel.cs, src/DemaConsulting.CanvasNet.Mermaid/Flowchart/FlowchartModel.Elements.cs, src/DemaConsulting.CanvasNet.Mermaid/Flowchart/FlowchartModel.LayoutData.cs, src/DemaConsulting.CanvasNet.Mermaid/Flowchart/FlowchartModel.Render.cs */
        comment testRef /* Test: test/DemaConsulting.CanvasNet.Mermaid.Tests/Flowchart/FlowchartModelTests.cs */
        comment designRef /* Design: docs/design/canvas-net-mermaid/flowchart/flowchart-model.md */
        comment verificationRef /* Verification: docs/verification/canvas-net-mermaid/flowchart/flowchart-model.md */
        comment reqRef /* Requirements: docs/reqstream/canvas-net-mermaid/flowchart/flowchart-model.yaml */
    }
}
