package CanvasNet {
    part def LabelBuilder {
        doc /* The internal LabelBuilder (a sealed partial class: the entry point and font metrics, HTML labels, markdown and plain strings, the markdown lexer of the marked subset Mermaid's labels use, and SVG labels) with the records LabelFont, LabelRequest, LabelRun, LabelLine, LabelImage, and LabelLayout: a port of Mermaid's createText.ts, handle-markdown-text.ts, and splitText.ts with the browser's layout of Mermaid's labels emulated over the bundled fonts of the call's FontResolver (Liberation Sans for Mermaid's default family names). Build first applies labelHelper's treatment to node labels (entity placeholders decoded, then sanitized), then lays the text out as an HTML label (markdown or plain HTML read into styled runs of b, strong, i, em, u and ins (underlined), br, img, span with a style, and p; other elements dropped with their text kept and reported as mermaid-html-tag-ignored; fa icon names removed; line boxes of 1.5 font sizes, centered lines, white space collapsed and unwrapped, else wrapped in a box of exactly the wrapping width with the core WordWrap after Mermaid's break-spaces retry; a picture alone five configured font sizes wide) or as an SVG label (Mermaid's lines split to the wrapping width, at characters for a long word, baselines 1.1 font sizes apart, and the box of the browser's getBBox with rounded metrics and glyph outlines, grown by 2 pixels with a background). An SVG label may inherit the font weight of its element (LabelRequest.SvgInheritsWeight), as the bold name of a class box does. Each SVG text run advances by its width rounded up to a 64th of a pixel (SvgRunAdvance), as the browser lays out SVG runs, also in SvgLineExtent; and the background of an SVG label whose own size differs from its root font size is measured in the root size, as Mermaid measures the text before the label takes its own size. A character that no bundled font has is reported once per label as mermaid-text-missing-glyph. The text utilities of Mermaid's utils.ts that sequence diagrams use are ported too (LabelBuilder.TextDimensions.cs): ParseFontSize, FontPixels, and SplitBreaks; CalculateTextDimensions and CalculateTextWidth, which measure each line as the browser's SVG text box rounded to whole pixels (white space collapsed, the advance grown to the hinted boxes of the end glyphs) and fail a zero font size as Mermaid's render does; and WrapLabel and BreakString, memoized with Mermaid's keys and with the state of Mermaid's line-break expression kept per builder, hyphenating long words at code points and charged to the optional layout work meter. ContainsFontAwesome finds a Font Awesome icon in a label as Mermaid does; the flowchart and the mindmap share it to report such icons. An instance belongs to one call on one thread. */

        comment sourceRef /* Source: src/DemaConsulting.CanvasNet.Mermaid/Rendering/LabelBuilder.cs, src/DemaConsulting.CanvasNet.Mermaid/Rendering/LabelBuilder.Html.cs, src/DemaConsulting.CanvasNet.Mermaid/Rendering/LabelBuilder.Markdown.cs, src/DemaConsulting.CanvasNet.Mermaid/Rendering/LabelBuilder.MarkdownLexer.cs, src/DemaConsulting.CanvasNet.Mermaid/Rendering/LabelBuilder.Svg.cs, src/DemaConsulting.CanvasNet.Mermaid/Rendering/LabelBuilder.TextDimensions.cs */
        comment testRef /* Test: test/DemaConsulting.CanvasNet.Mermaid.Tests/Rendering/LabelBuilderTests.cs */
        comment designRef /* Design: docs/design/canvas-net-mermaid/rendering/label-builder.md */
        comment verificationRef /* Verification: docs/verification/canvas-net-mermaid/rendering/label-builder.md */
        comment reqRef /* Requirements: docs/reqstream/canvas-net-mermaid/rendering/label-builder.yaml */
    }
}
