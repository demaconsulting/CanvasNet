package CanvasNet {
    part def ShapeLibrary {
        doc /* The internal static ShapeLibrary (a partial class: the entry point and style split, the classic and bracket shapes, the extended Mermaid shapes, the image and icon shapes, the intersect functions, the path parts and drafts, and the subgraph rectangle) with its value types ShapePoint, NodeBox, ShapeIntersect, NodePaint, ShapeTheme, ShapeContext, ShapeResult, and ClusterShape, and the shape registry ShapeNames (the 53 documented shapes with their short names, aliases, and internal aliases, and the undocumented shapes, with a case-sensitive IsKnown, HandlerOf, and the Nearest accepted name for a typo): a port of Mermaid's rendering-elements/shapes in the classic look. Draw measures the label through ShapeContext.MeasureLabel (labelHelper), computes the geometry from the label box, the padding, and the direction of the graph with Mermaid's formulas, paints the parts with the cascade of the style sheet's node rule, the node's own styles (styles2String split into label and node styles; declarations outside the CSS subset reported as mermaid-style-ignored), and the theme colors, and returns the drawn items, the box of everything drawn (the node size for the layout, as insertMeasuredNode), the label and its place, and the intersect function (rectangle, ellipse, circle, line, and polygon with Mermaid's arithmetic and quirks). Image nodes are sized from the natural size of NodeImages, w, h, and the aspect constraint; icons are not drawn but counted as a square of their size; rough.js circles are true circles, except the end state, whose rough.js outline is ported exactly (PathData.RoughEllipse); the legacy ellipse of A(-text-) is drawn as an ellipse; a shape of another diagram type fails with a located mermaid-render-failed that suggests a documented shape. The class box of a class diagram (ShapeLibrary.ClassBox.cs, a port of classBox.ts and textHelper) stacks the annotation, the bold name, the members, and the methods with the dividers between them, wraps each text at Mermaid's width measured through ShapeContext.TextWidth, underlines static and italicizes abstract members, draws HTML labels unless the top-level htmlLabels is false (then SVG labels spaced by the text padding), adds the extra compartment of an empty class unless class.hideEmptyMembersBox is set, and paints the rectangle and dividers with the class's own styles winning; the node size and the intersect come from its rectangle. The styles a diagram writes itself (LayoutNode.TrustedStyles, such as the alignment and paint of class notes) are applied without reports. The state shapes (ShapeLibrary.States.cs and the stateStart, stateEnd, forkJoin, choice, and note handlers, ports of Mermaid's state shapes) draw a state as a roundedRect with the padding of 8 and the CSS corner radius of the state sheet (insertNode turns a rect with both radii set into a roundedRect), a state with descriptions as rectWithTitle (the title, a divider, and the descriptions), the start circle, the end state's rough.js outline with its exact 14.013 width, the fork and join bars without the padding growth that Mermaid's measuring overwrites, the choice diamond, and the note, each painted through the state sheet's selectors with a Rules cascade and RoughPaint (a sheet's .node path rule over the rough.js attributes), so a sheet without those selectors keeps Mermaid's attribute paint; DrawCluster dispatches the state clusters roundedWithTitle (outer rectangle, title band, and inner area filled at alternate depths, widened to its title), divider (a dashed concurrent region), and noteGroup (an unpainted outline). The entity box (ShapeLibrary.ErBox.cs, a port of erBox.ts) draws an entity without attributes as a rectangle around its name at least er.minEntityWidth wide, and an entity with attributes as a table of the name row and type, name, keys, and comment columns (an unused keys or comment column left out), the paddings grown by 1.25 unless the top-level htmlLabels is set, SVG text when it is false, an empty SVG cell counted in the box as getBBox counts it, the rows filled in turn, and the dividers drawn as Mermaid draws them. The two shapes of a mindmap (ShapeLibrary.Mindmap.cs, ports of defaultMindmapNode.ts and mindmapCircle.ts) draw, in the classic look, a rectangle with corners rounded by 5 four times the padding wider than the label and the line along its bottom edge that only the sheet paints, and a circle with the whole node padding; a flowchart cannot name them. A node is painted by the sheet's rule for the SVG element its shape draws and the node's classes (UnifiedStyles.NodePaintFor and NodeLabelFor; only the mindmap sheet paints by classes), its label wraps at the node's Width when it is set (a mindmap's maxNodeWidth), and a node with an icon or a picture gives its SVG label the background. A node label's SVG text is centered on its anchor only when the sheet centers it (UnifiedStyles.CentersNodeSvgText). ShapeContext.Styles is the UnifiedStyles sheet of the diagram. DrawCluster draws the subgraph rectangle of clusters.js widened to its title. The class is stateless and safe for concurrent use. */

        comment sourceRef /* Source: src/DemaConsulting.CanvasNet.Mermaid/Rendering/ShapeLibrary.cs, src/DemaConsulting.CanvasNet.Mermaid/Rendering/ShapeLibrary.Basic.cs, src/DemaConsulting.CanvasNet.Mermaid/Rendering/ShapeLibrary.Extended.cs, src/DemaConsulting.CanvasNet.Mermaid/Rendering/ShapeLibrary.Images.cs, src/DemaConsulting.CanvasNet.Mermaid/Rendering/ShapeLibrary.Intersect.cs, src/DemaConsulting.CanvasNet.Mermaid/Rendering/ShapeLibrary.Parts.cs, src/DemaConsulting.CanvasNet.Mermaid/Rendering/ShapeLibrary.Clusters.cs, src/DemaConsulting.CanvasNet.Mermaid/Rendering/ShapeLibrary.ClassBox.cs, src/DemaConsulting.CanvasNet.Mermaid/Rendering/ShapeLibrary.States.cs, src/DemaConsulting.CanvasNet.Mermaid/Rendering/ShapeLibrary.ErBox.cs, src/DemaConsulting.CanvasNet.Mermaid/Rendering/ShapeLibrary.Mindmap.cs, src/DemaConsulting.CanvasNet.Mermaid/Rendering/ShapeNames.cs */
        comment testRef /* Test: test/DemaConsulting.CanvasNet.Mermaid.Tests/Rendering/ShapeLibraryTests.cs, test/DemaConsulting.CanvasNet.Mermaid.Tests/Rendering/ShapeLibraryVectorTests.cs, test/DemaConsulting.CanvasNet.Mermaid.Tests/Rendering/ShapeNamesTests.cs */
        comment designRef /* Design: docs/design/canvas-net-mermaid/rendering/shape-library.md */
        comment verificationRef /* Verification: docs/verification/canvas-net-mermaid/rendering/shape-library.md */
        comment reqRef /* Requirements: docs/reqstream/canvas-net-mermaid/rendering/shape-library.yaml */
    }
}
