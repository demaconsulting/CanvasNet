package CanvasNet {
    part def ClusterLayout {
        doc /* The internal ClusterLayout (a sealed partial class) with the graph labels ClusterLayoutNode and ClusterLayoutEdge, the result RenderedGraph, and the input records LayoutData, LayoutNode, and LayoutEdge (Mermaid's LayoutData, Node, and Edge): a port of Mermaid's dagre renderer (layout-algorithms/dagre/index.js with mermaid-graphlib.js). Render builds the root compound graph (nodesep and ranksep from the configuration, margins of 8, every node with its parent, and each self-loop as three segments through two hidden 10 by 10 labelRect nodes), records the subgraph table and descendants, marks the subgraphs an edge leaves or enters as having external connections, moves the links to such subgraphs onto anchor nodes (remembering the subgraph to cut at), and extracts every subgraph without external connections into a graph of its own (the direction it declares, else the other one of TB and LR; recursively to a depth of 10) represented by a clusterNode. Each graph is then measured (inner graphs first with the parent's nodesep and ranksep plus 25; every node drawn by ShapeLibrary in the direction of its graph; every edge label measured by EdgeBuilder), laid out with DagreLayout.Run, and painted: subgraph rectangles in sortNodesByHierarchy order through ShapeLibrary.DrawCluster with the title margins moving the contents down, the edges of getEdgesToRender (self-loops merged into one compact loop on the side the layout chose for the diagram types of shouldMergeSelfLoopSegments, else each segment drawn on its own) through EdgeBuilder, the edge labels each followed by its terminal labels, and the nodes and laid-out subgraphs (positionNode), as the layers clusters, edgePaths, edgeLabels, and nodes with the getBBox bounds of everything drawn. Every stage charges the render's LayoutWorkMeter (mermaid-limit-exceeded beyond MaxLayoutWork, cancellation observed); a subgraph cycle, a link to a subgraph without an anchor, and an edge whose end is not a node (CheckEnds, after the parents are set) fail with a located mermaid-render-failed where Mermaid's render fails. RenderDiagram (ClusterLayout.Diagram.cs) is the shared tail of the draw function of every unified diagram: the drawing, the diagram title centered above it at the title margin (insertTitle) with the box of its glyphs as SVG's getBBox gives it, and a view box of the drawn bounds grown by the diagram's padding. LayoutNode carries the class box texts (LayoutClassBox and LayoutClassMember), the trusted-styles flag, the radii, the centered label, and the descriptions of a state, and the entity box (LayoutErBox and LayoutErAttribute), and LayoutEdge the terminal labels. */

        comment sourceRef /* Source: src/DemaConsulting.CanvasNet.Mermaid/Rendering/ClusterLayout.cs, src/DemaConsulting.CanvasNet.Mermaid/Rendering/ClusterLayout.Extractor.cs, src/DemaConsulting.CanvasNet.Mermaid/Rendering/ClusterLayout.SelfLoops.cs, src/DemaConsulting.CanvasNet.Mermaid/Rendering/ClusterLayout.Diagram.cs, src/DemaConsulting.CanvasNet.Mermaid/Rendering/LayoutData.cs */
        comment testRef /* Test: test/DemaConsulting.CanvasNet.Mermaid.Tests/Rendering/ClusterLayoutTests.cs */
        comment designRef /* Design: docs/design/canvas-net-mermaid/rendering/cluster-layout.md */
        comment verificationRef /* Verification: docs/verification/canvas-net-mermaid/rendering/cluster-layout.md */
        comment reqRef /* Requirements: docs/reqstream/canvas-net-mermaid/rendering/cluster-layout.yaml */
    }
}
