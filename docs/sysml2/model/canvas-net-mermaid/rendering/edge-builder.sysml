package CanvasNet {
    part def EdgeBuilder {
        doc /* The internal static EdgeBuilder (a partial class: route, stroke, and labels; the d3-shape curves; the markers) with the records EdgeEnd, EdgeRoute, EdgeDrawing, EdgeLabelDrawing, and MarkerPaint and the path context ICurveContext and CurvePath: a port of Mermaid's edges.js, edgeMarker.ts, the flowchart markers of markers.js, lineWithOffset.ts, and the edge helpers of utils.ts, with the line generator and edge curves of d3-shape. Draw (insertEdge) replaces the first and last points of the layout's route with the intersections of the end nodes' outlines, cuts the route at the subgraph it enters or leaves (cutPathAtIntersect and intersection with their quirks), drops points whose y is not a number, rounds off right-angle corners (fixCorners), pulls the ends back by the marker offsets, and draws the points with the edge's curve (basis by default; linear, natural, step, stepBefore, stepAfter, monotoneX, monotoneY, cardinal, catmullRom, bumpX, bumpY, and rounded) as path data rounded to three decimals as d3-path writes it; the path is stroked by the style sheet's rules for its classes (edge-thickness, edge-pattern, an animation class drawn as its first frame) and its inline styles, and the point, circle, and cross markers (with start variants) are placed as SVG places them with orient auto, in the style sheet's marker paint or the first stroke of the edge's styles. MeasureLabel measures an edge label as insertEdgeLabel creates it (200 pixel wrapping width, with a background); LabelPosition places it at the layout's position or the middle of the changed route, moved by half the subgraph title margin; DrawLabel centers it over the backgrounds that the diagram's style sheet selects (a flowchart's paragraph and rectangle rules, a class diagram's label background, span, and rectangle rules). The class markers of markers.js (aggregation, extension, composition, dependency, and lollipop, with start variants) are drawn in user space with their reference points and colored by the relation's stroke. The terminal labels (EdgeBuilder.Terminals.cs, a port of calcTerminalLabelPosition and the terminal part of insertEdgeLabel and positionEdgeLabel) place the cardinalities beside the start and end of the route, the start label centered and the end label not, and a route too short to place them fails with a located mermaid-render-failed as Mermaid's render fails. The barb marker of state transitions is drawn in user space in the transition color of the state sheet's rules for its id, and the four ER cardinality markers (zero or one, exactly one, zero or more, one or more, at either end) in user space scaled with the line's stroke width, unfilled with white zero circles, without shortening the line, and with no marker for a parent end. An SVG edge label is centered on its text as drawn in its own size, its background measured in the root font size of the sheet (UnifiedStyles.RootText). The class is stateless and safe for concurrent use. */

        comment sourceRef /* Source: src/DemaConsulting.CanvasNet.Mermaid/Rendering/EdgeBuilder.cs, src/DemaConsulting.CanvasNet.Mermaid/Rendering/EdgeBuilder.Curves.cs, src/DemaConsulting.CanvasNet.Mermaid/Rendering/EdgeBuilder.Markers.cs, src/DemaConsulting.CanvasNet.Mermaid/Rendering/EdgeBuilder.Terminals.cs */
        comment testRef /* Test: test/DemaConsulting.CanvasNet.Mermaid.Tests/Rendering/EdgeBuilderTests.cs */
        comment designRef /* Design: docs/design/canvas-net-mermaid/rendering/edge-builder.md */
        comment verificationRef /* Verification: docs/verification/canvas-net-mermaid/rendering/edge-builder.md */
        comment reqRef /* Requirements: docs/reqstream/canvas-net-mermaid/rendering/edge-builder.yaml */
    }
}
