package CanvasNet {
    part def StateParser {
        doc /* The internal sealed StateParser (a partial class in two files) and the static StateTokens (the jison terminal names, their printed names and numbers): Parse reads the preprocessed text of a state diagram into a new StateModel. The lexer ports the 80 rules and the 20 start conditions of the lexer that jison generates from Mermaid's stateDiagram.jison, first match wins and case-insensitive for the keywords, with hand-written linear matchers in place of the regular expressions and Mermaid's quirks kept (a direction statement wherever the word stands on its line, an inline comment that ends an id, the pseudo-state forms, a note position in the case it is written in, a dash as the invalid token outside a composite state, and a click inside a composite state read as states). A recursive-descent parser accepts the language of the LALR(1) grammar under both headers (states, descriptions, the as form, transitions with labels, start and end states, composite states with their directions and concurrency dividers numbered in parse order, fork, join, and choice in both notations, notes, classDef, class, style, click, direction, the accessibility statements, and the statements Mermaid keeps as text) and builds the statement tree Mermaid's parser builds, reading statements in loops so that only nested composite states recurse. It checks the lookahead sets of jison's states first, so a token the grammar does not accept is a MermaidSyntaxException with code mermaid-syntax-error located in the original text, with jison's expected token names and a state hint; a note without its end is a located lexical error, a two-word composite name fails with Mermaid's message, and an unclosed composite state fails at the end. Composite states nested deeper than MaxNestingDepth and every kept text longer than MaxLabelLength are refused with mermaid-limit-exceeded. The detected id selects the legacy order of the model. An instance parses one text on one thread. */

        comment sourceRef /* Source: src/DemaConsulting.CanvasNet.Mermaid/State/StateParser.cs, src/DemaConsulting.CanvasNet.Mermaid/State/StateParser.Lexer.cs */
        comment testRef /* Test: test/DemaConsulting.CanvasNet.Mermaid.Tests/State/StateParserTests.cs, test/DemaConsulting.CanvasNet.Mermaid.Tests/State/StateVectorTests.cs (with the helper StateFacts.cs and the upstream vectors test/DemaConsulting.CanvasNet.Mermaid.Tests/Fixtures/upstream-vectors/state-parser.json) */
        comment designRef /* Design: docs/design/canvas-net-mermaid/state/state-parser.md */
        comment verificationRef /* Verification: docs/verification/canvas-net-mermaid/state/state-parser.md */
        comment reqRef /* Requirements: docs/reqstream/canvas-net-mermaid/state/state-parser.yaml */
    }
}
