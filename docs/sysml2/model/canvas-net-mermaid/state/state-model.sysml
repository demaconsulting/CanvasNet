package CanvasNet {
    part def StateModel {
        doc /* The internal sealed StateModel (a partial class in two files, implementing IMermaidDiagram) with its statement and database types StateStatement, StateNote, StateRecord, StateRelation, StateStyleClass, and StateLink, and the data fetcher's StateNode, StateNodeKind, and StateEdge: Mermaid's state database (stateDb.ts) and data fetcher (dataFetcher.ts) for one parsed text. SetRootDocument translates the statement tree as docTranslator does (each start and end state named after the document that holds it, a state used before its body made a composite state, the concurrent regions with generated ids, the statements kept after a trailing divider; for the legacy id the statements applied before the translation, as Mermaid's legacy database does), extracts the states with their types and descriptions, the transitions, notes, style classes, styles, and links (CheckLink keeps the URL of a click only as the shared UrlSanitizer of the Syntax subsystem checks it, its quotes removed and Mermaid's entity placeholders decoded, never as written, in the statement tree and the links alike), and runs the data fetcher: the nodes and edges of the layout with Mermaid's DOM ids from the counter the transitions share, each note in a note group of its own linked to its state, and a state that only a note names left without a shape. A description of a composite state beyond its title fails with Mermaid's message, located. The MaxNodes (states, composite states, concurrent regions, notes, and note groups together, a state that only a class statement names included), MaxEdges (transitions, the links of notes not counted), MaxNestingDepth (composite states and their regions, each a level), and MaxLabelLength (the descriptions joined under a title, the start and end ids, and the text styles it derives) limits are located MermaidSyntaxExceptions at open. The model gives the document its metadata (no title of its own, the accessible title, the last top-level direction, and the counts of states, transitions, and composite states, without notes, note groups, note links, or regions); GetData maps it for each render to the LayoutData of the Rendering subsystem as getData does (states with radius 10, padding 8, and a centered label, the first description as the label and the rest as descriptions, composite states and regions as clusters with their directions and alternate-depth classes, notes with the flowchart padding in note groups of padding 16, transitions with the barb end, the barb marker, and the state spacing, the diagram type stateDiagram for the legacy id too); ReportUnsupported reports, in order and located, the legacy renderer at the state settings, a look other than classic, and a layout other than dagre; and Layout reports first, fails a state without a shape located at its note (Mermaid's No such shape: undefined), then draws the layout input through the ClusterLayout with the label builder, the state style sheet, the node image loader, and the layout work meter of the render, with the frontmatter title at the state title margin and the padding of 8 of the state renderer. Once parsing is over the model is never changed and is safe for concurrent use. */

        comment sourceRef /* Source: src/DemaConsulting.CanvasNet.Mermaid/State/StateModel.cs, src/DemaConsulting.CanvasNet.Mermaid/State/StateModel.LayoutData.cs */
        comment testRef /* Test: test/DemaConsulting.CanvasNet.Mermaid.Tests/State/StateModelTests.cs */
        comment designRef /* Design: docs/design/canvas-net-mermaid/state/state-model.md */
        comment verificationRef /* Verification: docs/verification/canvas-net-mermaid/state/state-model.md */
        comment reqRef /* Requirements: docs/reqstream/canvas-net-mermaid/state/state-model.yaml */
    }
}
