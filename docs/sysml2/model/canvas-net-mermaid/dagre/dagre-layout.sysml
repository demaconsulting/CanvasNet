package CanvasNet {
    part def DagreLayout {
        doc /* The internal static partial DagreLayout class, the entry point of the layout and the port of dagre's layout.js and util.js. Run copies the caller's graph (DagreGraph, DagreNode, and DagreEdge labels, where a null attribute takes dagre's default: ranksep 50, edgesep 20, nodesep 50, rankdir tb, minlen 1, weight 1, labeloffset 10, labelpos r) into an internal compound multigraph of LayoutGraphLabel, LayoutNode, and LayoutEdge labels, runs dagre's stages in dagre's order (edge-label space, self-edge removal, cycle breaking, nesting graph, ranking, edge-label proxies, empty-rank removal, normalization, cluster chains and borders, ordering, self-edge insertion, the coordinate system, positioning, and the undo steps, translation, and node-border intersections), and writes back every node center, every cluster size, every edge route ending on the node borders, every label center, and the drawing size. The util.js helpers (AddDummyNode, Simplify, AsNonCompoundGraph, IntersectRect, BuildLayerMatrix, NormalizeRanks, RemoveEmptyRanks, MaxRank) serve every stage. The Lodash class reproduces V8's Array.prototype.sort steps (natural run, binary insertion to the minimum run length, stable merges without galloping) and lodash's sortBy, compareAscending, min, max, and minBy, so that ties are settled as in JavaScript. Run maps an InsufficientExecutionStackException to a located mermaid-limit-exceeded and dagre's own errors (InvalidOperationException) to a located mermaid-render-failed, and lets cancellation pass through. Faithful quirks of layout.js are kept (the _.max(a, b) of assignRankMinMax, the upper-case TB/BT test, the case-sensitive l/r fix-up, half-rank label proxies, and the translateGraph maximum starting at 0). */

        comment sourceRef /* Source: src/DemaConsulting.CanvasNet.Mermaid/Dagre/DagreLayout.cs, src/DemaConsulting.CanvasNet.Mermaid/Dagre/DagreLayout.Util.cs, src/DemaConsulting.CanvasNet.Mermaid/Dagre/DagreGraph.cs, src/DemaConsulting.CanvasNet.Mermaid/Dagre/LayoutModel.cs, src/DemaConsulting.CanvasNet.Mermaid/Dagre/Lodash.cs */
        comment testRef /* Test: test/DemaConsulting.CanvasNet.Mermaid.Tests/Dagre/DagreLayoutTests.cs, test/DemaConsulting.CanvasNet.Mermaid.Tests/Dagre/LodashTests.cs */
        comment designRef /* Design: docs/design/canvas-net-mermaid/dagre/dagre-layout.md */
        comment verificationRef /* Verification: docs/verification/canvas-net-mermaid/dagre/dagre-layout.md */
        comment reqRef /* Requirements: docs/reqstream/canvas-net-mermaid/dagre/dagre-layout.yaml */
    }
}
