package CanvasNet {
    part def MermaidSequence {
        doc /* The internal subsystem in the DemaConsulting.CanvasNet.Mermaid.Sequence namespace that reads and draws sequence diagrams (the sequenceDiagram keyword): a port of the sequence diagram of the pinned Mermaid release. The SequenceParser unit reads the preprocessed text with a port of the lexer of the generated sequenceDiagram.jison parser (its 94 rules and 8 start conditions as matchers that never backtrack) and a recursive-descent parser that accepts the language of its LALR(1) grammar with jison's error states and expected tokens, and collects the statements that it applies to the model after the whole text has parsed, as Mermaid does. The SequenceModel unit is Mermaid's sequence database (sequenceDb.ts): participants of the eight types with aliases, metadata, links, and properties, messages, notes, activations, block markers, boxes, created and destroyed participants, autonumber, wrap settings, and the title and accessibility texts, with Mermaid's errors located in the text and the MaxNodes, MaxNestingDepth, and MaxLabelLength limits; it gives the document its metadata (participants, messages drawn as arrows, and boxes as the node, edge, and subgraph counts, no direction) and, for each render, reports what is not drawn as Mermaid draws it (a look other than classic, participant image icons, $$ math, participants of an unknown type, the fo text placement) and has the layout draw the scene. The SequenceLayout unit ports Mermaid's sequenceRenderer.ts: the bounds model, the participant margins, the message, note, and block placement, activations, created and destroyed participants, mirrored and hidden participants, menus, sequence numbers, the title, and the view box, metered by the layout work meter. The SequenceRenderer unit ports svgDraw.js and svgDrawCommon.ts into scene items with Mermaid's roles and ids: the eight participant types, lifelines, messages with their markers, sequence numbers, central-connection circles, notes, activations, block frames, rect backgrounds, boxes with the theme's drop shadow, menus, and the text placements, painted from the theme's sequence style sheet in Mermaid's paint order. A parsed model is immutable and safe for concurrent renders. As of this release, its constituent units are SequenceParser, SequenceModel, SequenceLayout, and SequenceRenderer. */

        comment testRef /* Test: test/DemaConsulting.CanvasNet.Mermaid.Tests/Sequence/SequenceTests.cs (with the original fixtures test/DemaConsulting.CanvasNet.Mermaid.Tests/Fixtures/sequence/) */
        comment designRef /* Design: docs/design/canvas-net-mermaid/sequence.md */
        comment verificationRef /* Verification: docs/verification/canvas-net-mermaid/sequence.md */
        comment reqRef /* Requirements: docs/reqstream/canvas-net-mermaid/sequence.yaml */
        comment /* Within the CanvasNetMermaid system the Sequence subsystem depends on the Syntax subsystem (scanner, mapped text, YAML subset reader, HTML sanitizer, and the edit distance of the diagram detector), the Configuration subsystem (effective configuration with its sequence section, and the sequence style sheet), the Rendering subsystem (the text measuring and wrapping of the label builder), the Dagre subsystem (layout work meter), and the Scenegraph subsystem (scene types with drop shadows and stroked text); it is called by the document pipeline of the system. */

        part sequenceParser : SequenceParser;
        part sequenceModel : SequenceModel;
        part sequenceLayout : SequenceLayout;
        part sequenceRenderer : SequenceRenderer;
    }
}
