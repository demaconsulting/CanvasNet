package CanvasNet {
    part def SourceScanner {
        doc /* The internal SourceScanner of the Mermaid Syntax subsystem with the ScanMatcher delegate, ScanRule and ScanToken (SourceScanner.cs), the grouped ScanPatterns matcher building blocks, JavaScript character classes, and the letters outside ASCII of the UNICODE_TEXT rule that the flowchart and class grammars share (SourceScanner.Patterns.cs), the grouped TokenCursor one-token lookahead (SourceScanner.Tokens.cs), and the grouped UrlSanitizer link check (SourceScanner.Urls.cs). It is the lexer infrastructure that the diagram parsers build on, with the semantics of the lexers that jison generates for Mermaid's grammars: at each position the first rule of the active start condition that matches wins (not the longest), an action may change the state, the token text or the position (less), a stack of start conditions supports begin, popState and topState, and the end-of-input rule runs once before the scanner returns the end of input repeatedly. Every token's positions are positions of a MappedText, so they locate in the original text. Text that no rule matches is a located mermaid-syntax-error that describes the character found; TokenCursor.Expect refuses a token the grammar does not accept with a located mermaid-syntax-error whose Expected lists the accepted tokens in the grammar's words. A rule set that makes no progress is an InvalidOperationException (a defect of a grammar port). Every rule is a hand-written matcher, linear in what it inspects. UrlSanitizer is the link check every diagram applies to the links it keeps, an exact port of sanitizeUrl of the sanitize-url that Mermaid bundles with Mermaid's formatUrl at the strict security level: JavaScript's decodeURIComponent and the decoding loop (control characters, numeric character references read as String.fromCharCode reads them, newline and tab entities, escaped white space) until nothing is left to decode, relative links kept, the javascript, data, and vbscript schemes refused as about:blank in any case, backslashes as slashes, mailto and deep links kept, and http and https links written back by a port of the WHATWG URL parser (about:blank when it refuses them); host names outside ASCII go through .NET's IdnMapping, which is stricter than the browser's UTS 46 processing. */

        comment sourceRef /* Source: src/DemaConsulting.CanvasNet.Mermaid/Syntax/SourceScanner.cs, src/DemaConsulting.CanvasNet.Mermaid/Syntax/SourceScanner.Patterns.cs, src/DemaConsulting.CanvasNet.Mermaid/Syntax/SourceScanner.Tokens.cs, src/DemaConsulting.CanvasNet.Mermaid/Syntax/SourceScanner.Urls.cs */
        comment testRef /* Test: test/DemaConsulting.CanvasNet.Mermaid.Tests/Syntax/SourceScannerTests.cs */
        comment designRef /* Design: docs/design/canvas-net-mermaid/syntax/source-scanner.md */
        comment verificationRef /* Verification: docs/verification/canvas-net-mermaid/syntax/source-scanner.md */
        comment reqRef /* Requirements: docs/reqstream/canvas-net-mermaid/syntax/source-scanner.yaml */
    }
}
