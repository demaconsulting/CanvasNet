package CanvasNet {
    part def GitGraphParser {
        doc /* The internal sealed GitGraphParser (a partial class in three files) with the GitGraphToken, GitStatement, GitGraphDiagram, GitGraphDatabase, GitCommit, and GitBranch types: Parse reads the preprocessed text of a git graph into a new GitGraphDiagram. The lexer tries the keywords, longest first, then the accessibility, title, integer, string, and newline terminals, the hidden white space, YAML, directives, and comments, and last the REFERENCE terminal, in the order Langium gives chevrotain, first match wins, with hand-written linear matchers in place of the regular expressions; a keyword gives way to a REFERENCE only when the REFERENCE is strictly longer, and gitGraph must be followed by white space or a comment. A recursive-descent parser with one token of lookahead accepts the gitGraph grammar: the header gitGraph, gitGraph with a colon, or gitGraph with the direction LR, TB, or BT and a colon, then title and accessibility statements and the commit, branch, merge, checkout or switch, and cherry-pick statements with their id, msg, tag, type, order, and parent options; a repeated option keeps its last value and tags add up. Values are converted as the Mermaid value converters, Langium's convertString, and JavaScript's parseInt convert them. The statements run against GitGraphDatabase, a port of Mermaid's git graph database with the main branch name and order of the text's own configuration: ids, messages, branch names, tags, and parents sanitized as Mermaid's sanitizeText sanitizes them (merge tags kept as written); a commit whose id is already used replaces the earlier commit in its place; merge and cherry-pick messages and default tags composed as Mermaid composes them; a missing id generated as the sequence number, a dash, and seven hex digits of the mulberry32 sequence from a fixed seed, restarted for every run; branches sorted stably by their order for drawing; and every operation Mermaid's database rejects refused in Mermaid's order with Mermaid's message. A lexical error comes before any grammar error; grammar and database errors are MermaidSyntaxException values with code mermaid-syntax-error located in the original text and a hint, a grammar error with chevrotain's expected tokens. The main branch, every branch, and every commit count against MaxNodes, and every kept, converted, sanitized, or composed text and the frontmatter title against MaxLabelLength (mermaid-limit-exceeded). GitGraphDiagram is the IMermaidDiagram of the document: the commits as nodes, the parent links as edges, no subgraphs, the direction, the title (a title statement with a value replaces the frontmatter title), and the accessible title; Database gives the database of a render's configuration, the open one when the main branch name and order are the same, else the statements run again with a rejection reported as a located mermaid-render-failed; Layout draws it with GitGraphRenderer. An instance parses one text on one thread. */

        comment sourceRef /* Source: src/DemaConsulting.CanvasNet.Mermaid/GitGraph/GitGraphParser.cs, src/DemaConsulting.CanvasNet.Mermaid/GitGraph/GitGraphParser.Lexer.cs, src/DemaConsulting.CanvasNet.Mermaid/GitGraph/GitGraphParser.Database.cs */
        comment testRef /* Test: test/DemaConsulting.CanvasNet.Mermaid.Tests/GitGraph/GitGraphParserTests.cs, test/DemaConsulting.CanvasNet.Mermaid.Tests/GitGraph/GitGraphVectorTests.cs (with the upstream vectors test/DemaConsulting.CanvasNet.Mermaid.Tests/Fixtures/upstream-vectors/gitgraph-parser.json) */
        comment designRef /* Design: docs/design/canvas-net-mermaid/git-graph/git-graph-parser.md */
        comment verificationRef /* Verification: docs/verification/canvas-net-mermaid/git-graph/git-graph-parser.md */
        comment reqRef /* Requirements: docs/reqstream/canvas-net-mermaid/git-graph/git-graph-parser.yaml */
    }
}
