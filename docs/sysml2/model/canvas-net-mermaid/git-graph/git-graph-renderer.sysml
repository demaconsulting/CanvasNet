package CanvasNet {
    part def GitGraphRenderer {
        doc /* The internal sealed GitGraphRenderer (a partial class in three files): Draw turns a GitGraphDiagram into a scene for one render as Mermaid's git graph renderer (draw, drawCommits, drawBranches, drawArrows, and their helpers) does, with the database of the render's main branch name and order. In Mermaid's order: the branch positions (each branch 50 pixels after the one before, 40 more when the commit labels are rotated, and half its label's width more top to bottom or bottom to top); a first pass over the commits that only places them (each 50 pixels after the one before in the order of their sequence numbers, or with parallelCommits 40 pixels after its closest parent, bottom to top after the three loops of Mermaid's setParallelBTPos); the dashed branch lines and the branch labels on their rounded rectangles (one row per piece of the name, spaces kept); the arrows from the places of the first pass, bent once with radius 20 or, when a commit made between the two lies on the branch the arrow bends to, rerouted on a lane found as Mermaid's findLane finds it (lanes 10 pixels apart, at most six tries, the seventh candidate used untried); a second pass that places the commits again and draws their bullets by commit type (normal, reverse, highlight, merge, and cherry-pick), their labels on a half-transparent rectangle (turned by 45 degrees about the commit when rotateCommitLabel is set), and their tags on label shapes with a hole; and the title, centered over the bounding box of the drawing titleTopMargin above it. The two passes share their state as Mermaid's module state is shared, and Mermaid's Closest parent not found error is a located mermaid-render-failed. Texts are measured as the browser's getBBox measures them while Mermaid draws (with Mermaid's entity placeholders) and shown decoded; a rotated text is a SceneText with a SceneRotation and its box is the box of its turned box. The view box is the browser's bounding box of everything drawn (empty groups and texts left out, transformed boxes mapped, in single precision) grown by diagramPadding. The paint comes from the git graph style sheet, cascaded over the classes Mermaid gives each element (the commit id among them). The layout work meter of the render is charged for the branches, each commit of each pass and each parent looked at, each arrow and the commits its rerouting test scans, each lane try, and the measured texts, and checks cancellation. An instance draws one render on one thread. */

        comment sourceRef /* Source: src/DemaConsulting.CanvasNet.Mermaid/GitGraph/GitGraphRenderer.cs, src/DemaConsulting.CanvasNet.Mermaid/GitGraph/GitGraphRenderer.Arrows.cs, src/DemaConsulting.CanvasNet.Mermaid/GitGraph/GitGraphRenderer.Labels.cs */
        comment testRef /* Test: test/DemaConsulting.CanvasNet.Mermaid.Tests/GitGraph/GitGraphRendererTests.cs */
        comment designRef /* Design: docs/design/canvas-net-mermaid/git-graph/git-graph-renderer.md */
        comment verificationRef /* Verification: docs/verification/canvas-net-mermaid/git-graph/git-graph-renderer.md */
        comment reqRef /* Requirements: docs/reqstream/canvas-net-mermaid/git-graph/git-graph-renderer.yaml */
    }
}
