package CanvasNet {
    part def MermaidState {
        doc /* The internal subsystem in the DemaConsulting.CanvasNet.Mermaid.State namespace that reads state diagrams (the stateDiagram-v2 and stateDiagram keywords, and the legacy state id that a state.defaultRenderer other than dagre-wrapper selects) and lays them out through the shared unified renderer: a port of the state diagram of the pinned Mermaid release. The StateParser unit reads the preprocessed text with a port of the lexer of the generated stateDiagram.jison parser (its rules and start conditions as matchers that never backtrack) and a recursive-descent parser that accepts the language of its LALR(1) grammar with jison's error states and expected tokens, building the statement tree Mermaid's parser builds. The StateModel unit is Mermaid's state database (stateDb.ts) and data fetcher (dataFetcher.ts): it translates the statement tree (start and end ids named after their parents, concurrent regions, the legacy order for the legacy id), keeps states with descriptions, notes in note groups, style classes, styles, and links, fails on what Mermaid's database fails on, enforces the MaxNodes, MaxEdges, MaxNestingDepth, and MaxLabelLength limits (regions and note groups counted as nodes, regions as nesting levels), gives the document its metadata (states, transitions, and composite states as the node, edge, and subgraph counts, and the direction that lays the diagram out), maps the diagram for each render to the LayoutData of the Rendering subsystem as getData does, reports the legacy renderer, a look other than classic, and a layout other than dagre, fails a state without a shape located as Mermaid's render fails, and has the cluster layout draw the scene with the state style sheet, the title, and the padding of the state renderer. The state shapes, clusters, and the barb marker are drawn by the Rendering subsystem. A parsed model is immutable and safe for concurrent renders. As of this release, its constituent units are StateParser and StateModel. */

        comment testRef /* Test: test/DemaConsulting.CanvasNet.Mermaid.Tests/State/StateTests.cs (with the original fixtures test/DemaConsulting.CanvasNet.Mermaid.Tests/Fixtures/state/) */
        comment designRef /* Design: docs/design/canvas-net-mermaid/state.md */
        comment verificationRef /* Verification: docs/verification/canvas-net-mermaid/state.md */
        comment reqRef /* Requirements: docs/reqstream/canvas-net-mermaid/state.yaml */
        comment /* Within the CanvasNetMermaid system the State subsystem depends on the Syntax subsystem (scanner, mapped text, HTML sanitizing), the Configuration subsystem (effective configuration with its state section, the flowchart curve and padding, and the state style sheet), the Rendering subsystem (layout data, cluster layout, label builder, and node images), the Dagre subsystem (layout work meter), and the Scenegraph subsystem (scene types); it is called by the document pipeline of the system. */

        part stateParser : StateParser;
        part stateModel : StateModel;
    }
}
