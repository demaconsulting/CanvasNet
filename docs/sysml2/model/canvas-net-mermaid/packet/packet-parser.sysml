package CanvasNet {
    part def PacketParser {
        doc /* The internal sealed PacketParser (a partial class in two files) with the PacketToken, ParsedBlock, PacketBlock, and PacketDiagram types: Parse reads the preprocessed text of a packet diagram into a new PacketDiagram. The lexer tries the token types in the order Langium gives chevrotain (the keywords packet-beta, packet, which must be followed by white space or a comment, and the dash, plus, and colon, then the accessibility, title, integer, string, and newline terminals, then the hidden white space, YAML, directives, and comments), first match wins, with hand-written linear matchers in place of the regular expressions; a recursive-descent parser with one token of lookahead accepts the packet grammar. Values are converted as the Mermaid value converters and Langium's convertString and convertInt convert them, and the rules of Mermaid's packet database apply: each block filled in (a missing start is the next bit, a missing end the start plus the bit count less one) and refused, in Mermaid's order and with its messages, when its end is before its start, when it does not start at the bit after the block before it, or when it has zero bits; the title and accessibility texts sanitized. A lexical error comes before any grammar error; all are MermaidSyntaxException values with code mermaid-syntax-error located in the original text, a grammar error with chevrotain's expected tokens. Every block statement counts against MaxNodes, and every kept, converted, or sanitized text and the frontmatter title against MaxLabelLength (mermaid-limit-exceeded). PacketDiagram is the IMermaidDiagram of the document: the blocks as nodes and the title; Rows splits the blocks into rows of a given bitsPerRow exactly as Mermaid's populate and getNextFittingBlock do (a located mermaid-render-failed where Mermaid's split fails, MaxNodes and the layout work meter on the parts), and Layout draws it with PacketRenderer. An instance parses one text on one thread. */

        comment sourceRef /* Source: src/DemaConsulting.CanvasNet.Mermaid/Packet/PacketParser.cs, src/DemaConsulting.CanvasNet.Mermaid/Packet/PacketParser.Lexer.cs */
        comment testRef /* Test: test/DemaConsulting.CanvasNet.Mermaid.Tests/Packet/PacketParserTests.cs, test/DemaConsulting.CanvasNet.Mermaid.Tests/Packet/PacketVectorTests.cs (with the upstream vectors test/DemaConsulting.CanvasNet.Mermaid.Tests/Fixtures/upstream-vectors/packet-parser.json) */
        comment designRef /* Design: docs/design/canvas-net-mermaid/packet/packet-parser.md */
        comment verificationRef /* Verification: docs/verification/canvas-net-mermaid/packet/packet-parser.md */
        comment reqRef /* Requirements: docs/reqstream/canvas-net-mermaid/packet/packet-parser.yaml */
    }
}
