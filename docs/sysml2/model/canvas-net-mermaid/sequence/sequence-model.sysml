package CanvasNet {
    part def SequenceModel {
        doc /* The internal sealed SequenceModel (a partial class in four files, implementing IMermaidDiagram) with its constants SequenceLineType, SequencePlacement, and SequenceParticipantTypes, its elements SequenceText, SequenceActor, SequenceMessage, SequenceAutonumber, SequenceNote, SequenceBoxData, SequenceBox, and SequencePropertyMap, and the statement records that the parser collects: Mermaid's sequence database (sequenceDb.ts) for one parsed text. Applying the statements keeps Mermaid's semantics: participants in insertion order with their previous and next neighbors and box, a participant declared again replaced in place only with an alias, metadata types and aliases, implicit participants added by messages, the getMessages list of signals, notes, activations, central connections, block markers, and autonumber settings with their ids, the activation check, boxes with parseBoxData and the browser's color check (named and system colors and CSS color functions), created and destroyed participants with the index of the following message, links, link, and properties read as JSON with JavaScript key order, the wrap and nowrap prefixes, and the sanitized title and accessibility texts. Mermaid's database errors keep Mermaid's messages and become MermaidSyntaxExceptions located at the statement with a hint that names the participant; more participants and boxes together than MaxNodes, and a metadata type or alias longer than MaxLabelLength once converted to a string, are refused with mermaid-limit-exceeded. The model gives the document its metadata (the title of the title statement, the accessible title, participants as nodes, messages drawn as arrows as edges, boxes as subgraphs, no direction) and EffectiveWrap resolves a wrap setting against the configuration of a render. Layout reports a look other than classic, the fo text placement (a configuration warning), participants of an unknown type (a warning naming the nearest type), participant image icons, and $$ math (Mermaid's hasKatex), then has a SequenceLayout draw the scene. Once parsing is over the model is never changed and is safe for concurrent use. */

        comment sourceRef /* Source: src/DemaConsulting.CanvasNet.Mermaid/Sequence/SequenceModel.cs, src/DemaConsulting.CanvasNet.Mermaid/Sequence/SequenceModel.Elements.cs, src/DemaConsulting.CanvasNet.Mermaid/Sequence/SequenceModel.Statements.cs, src/DemaConsulting.CanvasNet.Mermaid/Sequence/SequenceModel.Render.cs */
        comment testRef /* Test: test/DemaConsulting.CanvasNet.Mermaid.Tests/Sequence/SequenceModelTests.cs */
        comment designRef /* Design: docs/design/canvas-net-mermaid/sequence/sequence-model.md */
        comment verificationRef /* Verification: docs/verification/canvas-net-mermaid/sequence/sequence-model.md */
        comment reqRef /* Requirements: docs/reqstream/canvas-net-mermaid/sequence/sequence-model.yaml */
    }
}
