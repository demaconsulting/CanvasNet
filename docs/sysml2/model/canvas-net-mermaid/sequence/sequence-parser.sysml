package CanvasNet {
    part def SequenceParser {
        doc /* The internal sealed SequenceParser (a partial class in three files) and the static SequenceTokens (the jison terminal names, their printed names and numbers, and the 26 arrows): Parse reads the preprocessed text of a sequence diagram into a new SequenceModel. The lexer ports the 94 rules and the start conditions of the lexer that jison generates from Mermaid's sequenceDiagram.jison, first match wins, with hand-written linear matchers in place of the regular expressions (the nested lookahead of participant names and the backtracking rules matched as the expressions match them), keywords with jison's automatic word boundary, and ASCII case folding. A recursive-descent parser accepts the language of the LALR(1) grammar (participants and actors with aliases, create, and @{ } metadata read through the YAML subset reader, destroy, boxes, autonumber, activate and deactivate, signals with every arrow and the activation shorthands, central connections, notes, the loop, alt, opt, par, par_over, critical, break, and rect blocks with their sections, links, link, properties, details, title, and the accessibility statements) and checks the merged lookahead sets of jison's states first, so a token the grammar does not accept is a MermaidSyntaxException with code mermaid-syntax-error located in the original text, with jison's expected token names in jison's order and a sequence hint; text no rule matches is a located lexical error. The title and accessibility texts are set during the parse; every other statement is collected and applied to the model after the whole parse, as yy.apply does, so grammar errors come before database errors. Blocks and boxes nested deeper than MaxNestingDepth and names or texts longer than MaxLabelLength are refused with mermaid-limit-exceeded. An instance parses one text on one thread. */

        comment sourceRef /* Source: src/DemaConsulting.CanvasNet.Mermaid/Sequence/SequenceParser.cs, src/DemaConsulting.CanvasNet.Mermaid/Sequence/SequenceParser.Lexer.cs, src/DemaConsulting.CanvasNet.Mermaid/Sequence/SequenceParser.Statements.cs */
        comment testRef /* Test: test/DemaConsulting.CanvasNet.Mermaid.Tests/Sequence/SequenceParserTests.cs, test/DemaConsulting.CanvasNet.Mermaid.Tests/Sequence/SequenceVectorTests.cs (with the helper SequenceFacts.cs and the upstream vectors test/DemaConsulting.CanvasNet.Mermaid.Tests/Fixtures/upstream-vectors/sequence-parser.json) */
        comment designRef /* Design: docs/design/canvas-net-mermaid/sequence/sequence-parser.md */
        comment verificationRef /* Verification: docs/verification/canvas-net-mermaid/sequence/sequence-parser.md */
        comment reqRef /* Requirements: docs/reqstream/canvas-net-mermaid/sequence/sequence-parser.yaml */
    }
}
