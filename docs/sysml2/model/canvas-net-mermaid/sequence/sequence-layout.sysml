package CanvasNet {
    part def SequenceLayout {
        doc /* The internal sealed SequenceLayout (a partial class in four files) with its layout state types SequenceBounds (Mermaid's bounds object), SequenceActorLayout, SequenceRectData, SequenceBoxLayout, SequenceMessageModel, SequenceNoteModel, SequenceLoopModel, SequenceLoopSection, SequenceActivation, and SequenceMessageState: a port of Mermaid's sequenceRenderer.ts for one render of a SequenceModel under the effective configuration of that render. Draw computes the participant sizes and the margins between neighbors from the measured message and note texts (calculateActorMargins), places the participants with the box margins and the created participants, walks the message list in order with the bounds model (message models, self messages as loops or right angles, notes, activations and their stacking, block starts, sections, and ends with the wrapped titles, the rect backgrounds, created and destroyed participants, sequence numbers from autonumber or showSequenceNumbers), draws the mirrored participants or runs the lifelines to 2000 without them, leaves out hidden unused participants, lays out the boxes and the menus (hidden menus still count in the size; forced menus are drawn), and computes the view box with the diagram margins and the room of the title. Every element is drawn through the SequenceRenderer, whose returned heights feed back into the layout as getBBox does in Mermaid; text is measured and wrapped with the LabelBuilder text utilities. The work is charged to the layout work meter of the render, which also checks for cancellation. An instance draws one render on one thread. */

        comment sourceRef /* Source: src/DemaConsulting.CanvasNet.Mermaid/Sequence/SequenceLayout.cs, src/DemaConsulting.CanvasNet.Mermaid/Sequence/SequenceLayout.Bounds.cs, src/DemaConsulting.CanvasNet.Mermaid/Sequence/SequenceLayout.Messages.cs, src/DemaConsulting.CanvasNet.Mermaid/Sequence/SequenceLayout.Blocks.cs */
        comment testRef /* Test: test/DemaConsulting.CanvasNet.Mermaid.Tests/Sequence/SequenceLayoutTests.cs */
        comment designRef /* Design: docs/design/canvas-net-mermaid/sequence/sequence-layout.md */
        comment verificationRef /* Verification: docs/verification/canvas-net-mermaid/sequence/sequence-layout.md */
        comment reqRef /* Requirements: docs/reqstream/canvas-net-mermaid/sequence/sequence-layout.yaml */
    }
}
