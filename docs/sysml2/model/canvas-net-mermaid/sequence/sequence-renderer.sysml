package CanvasNet {
    part def SequenceRenderer {
        doc /* The internal sealed SequenceRenderer (a partial class in five files) with SceneSlot and SequenceTextData: a port of Mermaid's svgDraw.js and svgDrawCommon.ts that turns what the SequenceLayout places into scene items with Mermaid's roles and ids, returning the heights that Mermaid measures with getBBox. It draws the eight participant types (participant boxes, the actor stick figure, boundary, control with its filled-head-control arrowhead, entity, database and queue cylinders, collections) with their lifelines, nothing for an unknown type, and a properties class in place of the actor class; messages as lines or self-loop paths with Mermaid's markers (arrowhead, crosshead, filled head, and the solid and stick half heads) at their ends, solid or dashed, sequence numbers in circles, and central-connection circles; notes and activations; block frames with dashed sides and section separators, the label box with its cut corner, and the keyword, title, and section titles (an empty block fails with mermaid-render-failed at its start); rect backgrounds and boxes behind everything in their colors (keyword and system colors with the browser's values) with the box border and the theme's drop shadow; menus as empty groups unless forceMenus draws the panel with its shadow and links (links on a type without a box fail as Mermaid fails); and texts with drawText, byTspan, and the old byText placement (stroked labels). The paint comes from the theme's SequenceStyles over Mermaid's attributes, and the items are kept in Mermaid's paint order, with lower() moving items to the back. An instance draws one render on one thread. */

        comment sourceRef /* Source: src/DemaConsulting.CanvasNet.Mermaid/Sequence/SequenceRenderer.cs, src/DemaConsulting.CanvasNet.Mermaid/Sequence/SequenceRenderer.Actors.cs, src/DemaConsulting.CanvasNet.Mermaid/Sequence/SequenceRenderer.Messages.cs, src/DemaConsulting.CanvasNet.Mermaid/Sequence/SequenceRenderer.Blocks.cs, src/DemaConsulting.CanvasNet.Mermaid/Sequence/SequenceRenderer.Text.cs */
        comment testRef /* Test: test/DemaConsulting.CanvasNet.Mermaid.Tests/Sequence/SequenceRendererTests.cs */
        comment designRef /* Design: docs/design/canvas-net-mermaid/sequence/sequence-renderer.md */
        comment verificationRef /* Verification: docs/verification/canvas-net-mermaid/sequence/sequence-renderer.md */
        comment reqRef /* Requirements: docs/reqstream/canvas-net-mermaid/sequence/sequence-renderer.yaml */
    }
}
