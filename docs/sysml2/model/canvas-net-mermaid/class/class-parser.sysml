package CanvasNet {
    part def ClassParser {
        doc /* The internal sealed ClassParser (a partial class in two files) and the static ClassTokens (the jison terminal names, their printed names and numbers): Parse reads the preprocessed text of a class diagram into a new ClassModel. The lexer ports the rules and the start conditions of the lexer that jison generates from Mermaid's classDiagram.jison, first match wins and case-sensitive, with hand-written linear matchers in place of the regular expressions and Mermaid's quirks kept (a direction anywhere on a line, keywords inside generics and backticks, a name of exactly o as an aggregation end, a class body line as one member, labels that run to the next colon, and the end of an open body). Names take the letters of the UNICODE_TEXT rule that the Syntax subsystem shares with the flowchart lexer. A recursive-descent parser accepts the language of the LALR(1) grammar (class statements with labels, generics, style classes, and bodies, member lines, relations with cardinalities and labels, lollipops, annotations, namespaces, notes, classDef, cssClass, style, click, link, callback, direction, and the accessibility statements), reading names, statements, members, and styles in loops so that only nested namespaces recurse. It checks the lookahead sets of jison's states first, so a token the grammar does not accept is a MermaidSyntaxException with code mermaid-syntax-error located in the original text, with jison's expected token names and a class hint; text no rule matches is a located lexical error. Each database action runs where jison reduces, after its lookahead check, so grammar and database errors come in Mermaid's order. Namespaces nested deeper than MaxNestingDepth (the model counts the dotted parts of their names too) and texts longer than MaxLabelLength are refused with mermaid-limit-exceeded. The text's own class.hierarchicalNamespaces setting is passed to the model for its counts. An instance parses one text on one thread. */

        comment sourceRef /* Source: src/DemaConsulting.CanvasNet.Mermaid/Class/ClassParser.cs, src/DemaConsulting.CanvasNet.Mermaid/Class/ClassParser.Lexer.cs */
        comment testRef /* Test: test/DemaConsulting.CanvasNet.Mermaid.Tests/Class/ClassParserTests.cs, test/DemaConsulting.CanvasNet.Mermaid.Tests/Class/ClassVectorTests.cs (with the helper ClassFacts.cs and the upstream vectors test/DemaConsulting.CanvasNet.Mermaid.Tests/Fixtures/upstream-vectors/class-parser.json) */
        comment designRef /* Design: docs/design/canvas-net-mermaid/class/class-parser.md */
        comment verificationRef /* Verification: docs/verification/canvas-net-mermaid/class/class-parser.md */
        comment reqRef /* Requirements: docs/reqstream/canvas-net-mermaid/class/class-parser.yaml */
    }
}
