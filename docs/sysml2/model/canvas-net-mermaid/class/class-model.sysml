package CanvasNet {
    part def ClassModel {
        doc /* The internal sealed ClassModel (a partial class in two files, implementing IMermaidDiagram) with its element types ClassNode, ClassMember, ClassRelation, ClassRelationInput, ClassRelationType, ClassNote, ClassInterface, ClassNamespace, and ClassStyleClass: Mermaid's class database (classDb.ts) for one parsed text. The database operations that the parser calls keep Mermaid's semantics: classes once in order of first mention with generic names split and DOM ids numbered per document, labels, members and methods split by Mermaid's ClassMember into display text, drawn text, and classifier style (underlined static, italic abstract), annotations, relations with end types, line type, cardinalities, and labels, an invisible interface node for each lollipop, namespaces with qualified ids and implicit dotted ancestors, notes, classDef styles applied to the classes that already carry the class, cssClass and style with Mermaid's DOM-id lookup, and link, tooltip, and callback data with only the link that the shared UrlSanitizer of the Syntax subsystem gives under the strict security level kept. What Mermaid's database fails on (an annotation of a missing class, a method text its expression cannot read) and the MaxEdges, MaxNodes (classes, notes, interfaces, and namespaces with their implicit ancestors, counted together as the flowchart counts nodes and subgraphs), and MaxLabelLength (the label of a generic class with its type, and the qualified id of a nested namespace, which are joined from texts checked apart), and MaxNestingDepth (the parts of a qualified namespace id, from nested keywords and dots in a name together, each a nested cluster) limits are located MermaidSyntaxExceptions at open. The model gives the document its metadata (no title of its own, the accessible title, the direction, and the counts of classes, relations, and the namespaces drawn under the text's own class.hierarchicalNamespaces); GetData maps it for each render to the LayoutData of the Rendering subsystem as getData does (namespaces as rect clusters in either namespace mode, classes as classBox nodes, notes and their links with the diagram's trusted styles, interface nodes, relations with markers and terminal labels and a minimum length of 1, the class markers, and the spacing the class renderer reads from the state section); ReportUnsupported reports, in order and located, a look other than classic and a layout other than dagre; and Layout reports first, then draws the layout input through the ClusterLayout with the label builder, the class style sheet, the node image loader, and the layout work meter of the render, with the frontmatter title and the padding of 8 of the class renderer. Once parsing is over the model is never changed and is safe for concurrent use. */

        comment sourceRef /* Source: src/DemaConsulting.CanvasNet.Mermaid/Class/ClassModel.cs, src/DemaConsulting.CanvasNet.Mermaid/Class/ClassModel.LayoutData.cs */
        comment testRef /* Test: test/DemaConsulting.CanvasNet.Mermaid.Tests/Class/ClassModelTests.cs */
        comment designRef /* Design: docs/design/canvas-net-mermaid/class/class-model.md */
        comment verificationRef /* Verification: docs/verification/canvas-net-mermaid/class/class-model.md */
        comment reqRef /* Requirements: docs/reqstream/canvas-net-mermaid/class/class-model.yaml */
    }
}
