package CanvasNet {
    part def MermaidDocument {
        doc /* The public API of CanvasNetMermaid in the DemaConsulting.CanvasNet.Mermaid namespace: the sealed, immutable, thread-safe MermaidDocument with the static Parse(string), Open(string path), and Open(Stream) entry points (strict UTF-8, byte-order mark dropped, bounded reads), the metadata properties (SourceName, DiagramType, IsSupported, Title, AccTitle, Direction, NodeCount, EdgeCount, SubgraphCount), Measure, Render, and Render(width, height); the validated MermaidOpenOptions, MermaidRenderOptions (Scale, Background, Config, Theme, ImageResolver, Now, the only clock, which a gantt chart reads for today, Limits, handlers, strict mode), and MermaidLimits; the MermaidLocation, MermaidDiagnostic, MermaidUnsupportedFeature, and MermaidSize records; the MermaidDiagnosticCodes constants; the MermaidSyntaxException, MermaidRenderException, and MermaidUnsupportedFeatureException types; the internal MermaidReportSink (ordered, de-duplicated, capped delivery on the calling thread) and pipeline seam (IMermaidDiagram, DiagramRenderContext, and DiagramRegistry, which hands each supported type to its parser - the flowchart, sequence, class, state, ER, pie, gantt, mindmap, packet, and git graph parsers - with the configuration of the text itself for the counts that depend on it and for the main branch name and order of a git graph); and the MermaidImageSource for .mmd and .mermaid files with the theme fragment parameter. */

        comment sourceRef /* Source: src/DemaConsulting.CanvasNet.Mermaid/MermaidDocument.cs, src/DemaConsulting.CanvasNet.Mermaid/MermaidDocument.Render.cs, src/DemaConsulting.CanvasNet.Mermaid/MermaidDocument.Pipeline.cs, src/DemaConsulting.CanvasNet.Mermaid/MermaidOpenOptions.cs, src/DemaConsulting.CanvasNet.Mermaid/MermaidRenderOptions.cs, src/DemaConsulting.CanvasNet.Mermaid/MermaidLimits.cs, src/DemaConsulting.CanvasNet.Mermaid/MermaidLocation.cs, src/DemaConsulting.CanvasNet.Mermaid/MermaidDiagnostic.cs, src/DemaConsulting.CanvasNet.Mermaid/MermaidUnsupportedFeature.cs, src/DemaConsulting.CanvasNet.Mermaid/MermaidSize.cs, src/DemaConsulting.CanvasNet.Mermaid/MermaidDiagnosticCodes.cs, src/DemaConsulting.CanvasNet.Mermaid/MermaidSyntaxException.cs, src/DemaConsulting.CanvasNet.Mermaid/MermaidRenderException.cs, src/DemaConsulting.CanvasNet.Mermaid/MermaidUnsupportedFeatureException.cs, src/DemaConsulting.CanvasNet.Mermaid/MermaidReportSink.cs, src/DemaConsulting.CanvasNet.Mermaid/MermaidImageSource.cs, src/DemaConsulting.CanvasNet.Mermaid/NamespaceDoc.cs */
        comment testRef /* Test: test/DemaConsulting.CanvasNet.Mermaid.Tests/MermaidDocumentTests.cs, test/DemaConsulting.CanvasNet.Mermaid.Tests/MermaidRenderOptionsTests.cs, test/DemaConsulting.CanvasNet.Mermaid.Tests/MermaidLimitsTests.cs, test/DemaConsulting.CanvasNet.Mermaid.Tests/MermaidRecordsAndExceptionsTests.cs, test/DemaConsulting.CanvasNet.Mermaid.Tests/MermaidReportSinkTests.cs, test/DemaConsulting.CanvasNet.Mermaid.Tests/MermaidImageSourceTests.cs */
        comment designRef /* Design: docs/design/canvas-net-mermaid/mermaid-document.md */
        comment verificationRef /* Verification: docs/verification/canvas-net-mermaid/mermaid-document.md */
        comment reqRef /* Requirements: docs/reqstream/canvas-net-mermaid/mermaid-document.yaml */
    }
}
