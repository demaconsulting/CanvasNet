package CanvasNet {
    part def CoseLayout {
        doc /* The internal sealed CoseLayout (a partial class in six files) with the records CoseSize, CoseLink, CosePoint, CoseEdgePoints, and CoseResult: Run lays out one tree as Mermaid's cose-bilkent layout lays out a mindmap in the browser and returns the node centers in node order, the edge points in edge order, and the number of iterations. The options in effect are cose-bilkent's defaults with Mermaid's quality proof and animate false (the ideal edge length 50, the spring constant 0.45, the repulsion constant 4,500, the iteration limit 2,500 raised to five per node beyond 500 nodes, the convergence check every 100 iterations, the grid rebuilt every 10 iterations, the graph margin 15, and the world boundary 1,000,000). Run checks that the input is one tree, builds the root graph, finds the flat forest and the center of the tree, places the nodes radially around it, runs the spring embedder (the spring and repulsion forces, the repulsion grid, the cooling schedule, and the clamp to the world boundary) until it converges or reaches its limit, and moves the drawing so that its top-left corner less the margin is at the origin. The edge points are cytoscape's straight-edge points: where the line between the centers crosses the circle of radius 15 around each center, with the middle between them, and NaN when the centers are 15 pixels apart or closer. JavaScript's operation order and number semantics are kept (parseInt through the string of a number, NaN comparisons, Integer.MAX_VALUE bounds), and Sin, Cos, Log, and Pow are correctly rounded, never computed with the host's math library, so the result is the same on every platform. Every step charges the layout work meter (the input, the searches, each iteration, every repulsion pair, every grid cell, and every transcendental function), which observes cancellation; a grid JavaScript could not build or a math argument outside its domain fails as mermaid-render-failed, and a radial recursion that would exhaust the stack as mermaid-limit-exceeded. An instance serves one call on one thread; the math functions are pure. */

        comment sourceRef /* Source: src/DemaConsulting.CanvasNet.Mermaid/Cose/CoseLayout.cs, src/DemaConsulting.CanvasNet.Mermaid/Cose/CoseLayout.Graph.cs, src/DemaConsulting.CanvasNet.Mermaid/Cose/CoseLayout.Radial.cs, src/DemaConsulting.CanvasNet.Mermaid/Cose/CoseLayout.Forces.cs, src/DemaConsulting.CanvasNet.Mermaid/Cose/CoseLayout.Edges.cs, src/DemaConsulting.CanvasNet.Mermaid/Cose/CoseLayout.Math.cs */
        comment testRef /* Test: test/DemaConsulting.CanvasNet.Mermaid.Tests/Cose/CoseLayoutTests.cs, test/DemaConsulting.CanvasNet.Mermaid.Tests/Cose/CoseGoldenTests.cs (with the upstream vectors test/DemaConsulting.CanvasNet.Mermaid.Tests/Fixtures/upstream-vectors/cose-layouts.json and test/DemaConsulting.CanvasNet.Mermaid.Tests/Fixtures/upstream-vectors/js-math.json) */
        comment designRef /* Design: docs/design/canvas-net-mermaid/cose/cose-layout.md */
        comment verificationRef /* Verification: docs/verification/canvas-net-mermaid/cose/cose-layout.md */
        comment reqRef /* Requirements: docs/reqstream/canvas-net-mermaid/cose/cose-layout.yaml */
    }
}
