package CanvasNet {
    part def GanttModel {
        doc /* The internal sealed GanttModel (a partial class in three files) with GanttStartKind, GanttRawTask, GanttTask, the date compiler, GanttClock, and the static Dayjs: Mermaid's gantt database and the IMermaidDiagram of a gantt chart. It keeps the statements as the grammar passes them, the excludes and includes tokens merged across statements, the sections, and the tasks split into their tags (active, done, crit, milestone, vert), id (task1, task2, and so on when none is given), start, and end, with the rows of the tasks (a vertical marker takes none) and the ids in a JavaScript object (a later id replaces an earlier one, __proto__ is never found); a click adds the clickable class and an href is kept only as the shared link check of Mermaid's strict security level gives it, never drawn and never bound. Its metadata are the title, the accessible title, the tasks as nodes, and the drawn sections as subgraphs. For each render, Compile computes the task dates as Mermaid's getTasks does in up to eleven passes: dates in the dateFormat by the strict parse of the dayjs customParseFormat plugin, timestamps, and ECMAScript date texts; durations added as dayjs adds them; after and until references; ends moved past excluded weekends, weekdays, and dates that are not included; inclusive end dates; all in UTC with today from GanttClock, which takes it only from MermaidRenderOptions.Now and otherwise takes 1970-01-01 and reports mermaid-gantt-today-unavailable once. Where Mermaid's compilation fails or leaves a task without dates (an invalid date, the first task without a start, excluded days that never end, circular references) it throws a MermaidRenderException with code mermaid-render-failed located at the task; every date loop, reference, and pass is charged to the layout work meter, and the derived class lists and links are checked against MaxLabelLength. The model is never changed after parsing and is safe for concurrent renders. */

        comment sourceRef /* Source: src/DemaConsulting.CanvasNet.Mermaid/Gantt/GanttModel.cs, src/DemaConsulting.CanvasNet.Mermaid/Gantt/GanttModel.Tasks.cs, src/DemaConsulting.CanvasNet.Mermaid/Gantt/GanttModel.Dayjs.cs */
        comment testRef /* Test: test/DemaConsulting.CanvasNet.Mermaid.Tests/Gantt/GanttModelTests.cs, test/DemaConsulting.CanvasNet.Mermaid.Tests/Gantt/GanttVectorTests.cs (with the upstream vectors test/DemaConsulting.CanvasNet.Mermaid.Tests/Fixtures/upstream-vectors/gantt-parser.json) */
        comment designRef /* Design: docs/design/canvas-net-mermaid/gantt/gantt-model.md */
        comment verificationRef /* Verification: docs/verification/canvas-net-mermaid/gantt/gantt-model.md */
        comment reqRef /* Requirements: docs/reqstream/canvas-net-mermaid/gantt/gantt-model.yaml */
    }
}
