package CanvasNet {
    part def GanttRenderer {
        doc /* The internal sealed GanttRenderer (a partial class in three files): Draw turns a GanttModel into a scene for one render as Mermaid's gantt renderer does, after compiling the task dates with the clock of the render. The chart is 784 pixels wide (the container of mermaid-cli's page) unless gantt.useWidth is set, and has a row of the bar height and gap for each task that is not a vertical marker (in compact mode, as many rows as the most overlapping tasks of a section) between two top paddings. A time scale with whole-pixel rounding and no nice maps the earliest start to the latest end; tasks are drawn in order of their start, vertical markers last, over the background rows of their sections, as rounded bars with the class strings of their states, milestones as turned squares, and vertical markers as thin bars over all rows; a task text is inside its bar when it fits, else to its right, or to its left when it would leave the chart. The section titles follow JavaScript object-key order and split at br tags; excluded days are shaded unless the chart spans more than five years (then mermaid-gantt-excludes-skipped); the d3-axis bottom axis, and a top axis with topAxis, carry the grid with labels in the axis format, and a tickInterval that would give more than 10,000 ticks falls back to the default ticks (mermaid-gantt-ticks-skipped); the today line is drawn only with MermaidRenderOptions.Now (a todayMarker style without it is reported as mermaid-gantt-today-unavailable), and the title comes last. The paint comes from the cascade of the gantt style sheet with the element opacity folded into the colors. The layout work meter is charged for the excluded days, the ticks and their labels, the compact rows, the sorts, and the measured texts, each tick label is checked against MaxLabelLength, and a compact section named like an inherited JavaScript member fails located as mermaid-render-failed. An instance draws one render on one thread. */

        comment sourceRef /* Source: src/DemaConsulting.CanvasNet.Mermaid/Gantt/GanttRenderer.cs, src/DemaConsulting.CanvasNet.Mermaid/Gantt/GanttRenderer.Tasks.cs, src/DemaConsulting.CanvasNet.Mermaid/Gantt/GanttRenderer.Axis.cs */
        comment testRef /* Test: test/DemaConsulting.CanvasNet.Mermaid.Tests/Gantt/GanttRendererTests.cs */
        comment designRef /* Design: docs/design/canvas-net-mermaid/gantt/gantt-renderer.md */
        comment verificationRef /* Verification: docs/verification/canvas-net-mermaid/gantt/gantt-renderer.md */
        comment reqRef /* Requirements: docs/reqstream/canvas-net-mermaid/gantt/gantt-renderer.yaml */
    }
}
