package CanvasNet {
    part def ErModel {
        doc /* The internal sealed ErModel (a partial class in two files, implementing IMermaidDiagram) with its element types ErEntity, ErAttribute, ErRelationship, ErRelationshipSpec, ErStyleClass, and ErSubgraph: Mermaid's ER database (erDb.ts) for one parsed text. The database operations that the parser calls keep Mermaid's semantics: entities once in order of first mention with ids numbered by the entities before them, the first alias, and attributes that repeated blocks add to; relationships with their cardinalities, line types, and roles, an end named after a subgraph using the subgraph's id and adding an entity of that name that takes a number but is not drawn; subgraphs with their trimmed ids, sanitized and trimmed titles, directions, and nodes (the trimmed statement values without duplicates or the nodes of the subgraphs that end before them); and classDef, class, and style statements with the default class first and a color making a text style with fill as bgFill. The MaxNodes (entities, those named after a subgraph included, and subgraphs together), MaxEdges (relationships), and MaxLabelLength (text styles, the joined classes of an entity or a subgraph, and the compiled styles joined at completion) limits are located MermaidSyntaxExceptions at open. The model gives the document its metadata (no title of its own, the accessible title, the last top-level direction, and the counts of drawn entities, relationships, and subgraphs); GetData maps it for each render to the LayoutData of the Rendering subsystem as getData does (the subgraphs first as clusters, the last one first, each node in the first subgraph that holds it; entities as erBox nodes with LayoutErBox and LayoutErAttribute; relationships with the ER marker of the left cardinality at the start and of the right one at the end, md_parent with none, their line patterns and roles; and the spacing of the er section with a top-level nodeSpacing or rankSpacing winning); ReportUnsupported reports, in order and located, a look other than classic and a layout other than dagre; and Layout reports first, then draws the layout input through the ClusterLayout with the label builder, the ER style sheet, the text width of calculateTextWidth, the node image loader, and the layout work meter of the render, with the frontmatter title at the er title margin and the padding of 8 of the ER renderer. Once parsing is over the model is never changed and is safe for concurrent use. */

        comment sourceRef /* Source: src/DemaConsulting.CanvasNet.Mermaid/Er/ErModel.cs, src/DemaConsulting.CanvasNet.Mermaid/Er/ErModel.LayoutData.cs */
        comment testRef /* Test: test/DemaConsulting.CanvasNet.Mermaid.Tests/Er/ErModelTests.cs */
        comment designRef /* Design: docs/design/canvas-net-mermaid/er/er-model.md */
        comment verificationRef /* Verification: docs/verification/canvas-net-mermaid/er/er-model.md */
        comment reqRef /* Requirements: docs/reqstream/canvas-net-mermaid/er/er-model.yaml */
    }
}
