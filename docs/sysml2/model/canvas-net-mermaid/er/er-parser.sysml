package CanvasNet {
    part def ErParser {
        doc /* The internal sealed ErParser (a partial class in two files) and the static ErTokens (the jison terminal names, their printed names and numbers): Parse reads the preprocessed text of an entity relationship diagram into a new ErModel. The lexer ports the rules and the start conditions of the lexer that jison generates from Mermaid's erDiagram.jison, first match wins, with hand-written linear matchers in place of the regular expressions and Mermaid's quirks kept (the cardinalities in symbols and words in the rule order, the left one read as the second cardinality, names that start like keywords read as names, keywords in any case, a direction statement wherever it stands on its line, and a generic attribute type that runs to the last tilde of its line). A recursive-descent parser accepts the language of the LALR(1) grammar (entities with aliases, classes, and attribute blocks with types, names, keys, and comments; relationships with identifying or non-identifying lines and quoted or one-word roles; subgraphs whose statement values are their nodes; classDef, class, style, direction, and the accessibility statements), reading statements in loops so that only nested subgraphs recurse. It checks the lookahead sets of jison's states first, so a token the grammar does not accept is a MermaidSyntaxException with code mermaid-syntax-error located in the original text, with jison's expected token names and an ER hint; text no rule matches is a located lexical error, and an unclosed subgraph fails at the end. Subgraphs nested deeper than MaxNestingDepth and every kept or joined text longer than MaxLabelLength are refused with mermaid-limit-exceeded. Each database action runs where jison reduces, after its lookahead check, so grammar and database errors come in Mermaid's order. An instance parses one text on one thread. */

        comment sourceRef /* Source: src/DemaConsulting.CanvasNet.Mermaid/Er/ErParser.cs, src/DemaConsulting.CanvasNet.Mermaid/Er/ErParser.Lexer.cs */
        comment testRef /* Test: test/DemaConsulting.CanvasNet.Mermaid.Tests/Er/ErParserTests.cs, test/DemaConsulting.CanvasNet.Mermaid.Tests/Er/ErVectorTests.cs (with the helper ErFacts.cs and the upstream vectors test/DemaConsulting.CanvasNet.Mermaid.Tests/Fixtures/upstream-vectors/er-parser.json) */
        comment designRef /* Design: docs/design/canvas-net-mermaid/er/er-parser.md */
        comment verificationRef /* Verification: docs/verification/canvas-net-mermaid/er/er-parser.md */
        comment reqRef /* Requirements: docs/reqstream/canvas-net-mermaid/er/er-parser.yaml */
    }
}
