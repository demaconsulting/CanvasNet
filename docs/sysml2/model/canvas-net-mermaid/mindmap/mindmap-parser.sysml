package CanvasNet {
    part def MindmapParser {
        doc /* The internal sealed MindmapParser (a partial class in two files) with the MindmapTokens names and the MindmapNodeType, MindmapNode, MindmapEdge, and MindmapDiagram types: Parse reads the preprocessed text of a mindmap into a new MindmapDiagram. The lexer applies the 37 rules of Mermaid's generated jison lexer with their five start conditions (CLASS, ICON, NODE, NSTR, and NSTR2), case-insensitive, first match wins, with hand-written matchers that cannot backtrack in place of the regular expressions, so a text splits into the same tokens as in Mermaid, quirks included; a recursive-descent parser with one token of lookahead accepts the language of the LALR grammar and checks each lookahead against the actions of the LALR state jison is in. Each database call is made where jison reduces: as in Mermaid's addNode, the first node is the root and sets the base level, every other node's parent is the last node with a smaller level, and the node types, the last icon, and the last class are kept, sanitized. The diagram derives what Mermaid's getData derives: the sections that cycle through 11 among the root's children and are inherited below, the node classes, and the edges with their section and depth classes. A lexical or grammar error (with Mermaid's expected tokens), a second root, and a decoration before any node are MermaidSyntaxException values with code mermaid-syntax-error located in the original text; every node counts against MaxNodes, its depth against MaxNestingDepth, and every kept, sanitized, or joined text against MaxLabelLength (mermaid-limit-exceeded). MindmapDiagram is the IMermaidDiagram of the document: the nodes, one fewer edges, no subgraphs, title, or direction, and Layout draws it with MindmapRenderer. An instance parses one text on one thread; reading a text is linear in its length and never recursive. */

        comment sourceRef /* Source: src/DemaConsulting.CanvasNet.Mermaid/Mindmap/MindmapParser.cs, src/DemaConsulting.CanvasNet.Mermaid/Mindmap/MindmapParser.Lexer.cs */
        comment testRef /* Test: test/DemaConsulting.CanvasNet.Mermaid.Tests/Mindmap/MindmapParserTests.cs, test/DemaConsulting.CanvasNet.Mermaid.Tests/Mindmap/MindmapVectorTests.cs (with the upstream vectors test/DemaConsulting.CanvasNet.Mermaid.Tests/Fixtures/upstream-vectors/mindmap-parser.json) */
        comment designRef /* Design: docs/design/canvas-net-mermaid/mindmap/mindmap-parser.md */
        comment verificationRef /* Verification: docs/verification/canvas-net-mermaid/mindmap/mindmap-parser.md */
        comment reqRef /* Requirements: docs/reqstream/canvas-net-mermaid/mindmap/mindmap-parser.yaml */
    }
}
