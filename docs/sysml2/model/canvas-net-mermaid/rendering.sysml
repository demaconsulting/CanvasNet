package CanvasNet {
    part def MermaidRendering {
        doc /* The internal Rendering subsystem in the DemaConsulting.CanvasNet.Mermaid.Rendering namespace: the diagram-independent geometry of Mermaid's unified renderer (rendering-util), which lays out and draws the layout data that a diagram model hands it and returns the drawn diagram as scene items with the box of everything drawn. The ClusterLayout unit is Mermaid's dagre renderer: it turns the LayoutData records (nodes, subgraphs, edges, and the effective configuration) into compound graphs, moves links to subgraphs onto anchor nodes and cuts them at the subgraph borders, lays out the subgraphs without links to the outside on their own in their own direction, lays out self-loops through hidden nodes and draws them as compact loops, sizes every node and edge label, runs the dagre layout within the layout work budget, and draws the subgraph rectangles, edges, edge labels, and nodes in Mermaid's layers. It also frames a drawn diagram with its title and padded view box, merges self-loops only for the diagram types whose Mermaid renderer merges them, and fails, located, an edge whose end is not drawn. The ShapeLibrary unit draws every node shape a flowchart can name (the 53 documented shapes with their aliases in the ShapeNames registry, the bracket shapes, and the undocumented shapes) the class box of a class diagram, the state shapes and the composite state, concurrent region, and note group clusters of a state diagram, the entity box of an entity relationship diagram, and the two shapes of a mindmap (defaultMindmapNode and mindmapCircle), sized from its label and padding, painted by the style sheet and the node's styles, with Mermaid's intersect functions, and the subgraph rectangle with its title. The EdgeBuilder unit draws the edges: the route cut at the node outlines and subgraph borders, the d3-shape curve with three-decimal path data, the link stroke and edge styles, the point, circle, and cross markers of flowcharts, the class markers, the barb of state transitions, and the ER cardinality markers, the edge labels with the backgrounds of the diagram's style sheet, and the cardinalities at the ends of a class relation. The LabelBuilder unit lays out and measures plain, markdown, HTML, and SVG label text as Mermaid's createText does with the bundled fonts (SVG runs on the browser's 64th-of-a-pixel grid), reporting unsupported HTML elements and missing glyphs. The NodeImages unit loads the pictures of image nodes and labels only through the caller's image resolver, with their natural sizes, the device-size loads of the painter, the unresolved-picture report, and the MaxImages limit. A mindmap, which Mermaid lays out with cose-bilkent rather than dagre, uses the shapes, labels, and edges of the subsystem directly: the MindmapRenderer unit of the Mindmap subsystem draws each node with ShapeLibrary and each edge with EdgeBuilder through the points of the Cose layout, without ClusterLayout; the Rendering subsystem does not call the Cose subsystem. The subsystem paints nothing itself; the Scenegraph painter draws the scene. As of this release, its constituent units are ClusterLayout, ShapeLibrary, EdgeBuilder, LabelBuilder, and NodeImages. */

        comment testRef /* Test: test/DemaConsulting.CanvasNet.Mermaid.Tests/Rendering/RenderingTests.cs */
        comment designRef /* Design: docs/design/canvas-net-mermaid/rendering.md */
        comment verificationRef /* Verification: docs/verification/canvas-net-mermaid/rendering.md */
        comment reqRef /* Requirements: docs/reqstream/canvas-net-mermaid/rendering.yaml */
        comment /* Within the CanvasNetMermaid system this subsystem consumes the Dagre subsystem (DagreLayout and the LayoutWorkMeter), the Graphlib subsystem (compound graphs), the Configuration subsystem (MermaidConfig, FlowchartStyles and the other unified style sheets such as MindmapStyles, and StyleDeclarations), the Syntax subsystem (HtmlSanitizer), and the Scenegraph subsystem (scene items and ISceneImageLoader), and the core CanvasNet public API (Rgba32, Surface, FontResolver, TextRenderer, WordWrap, and IImageResolver). The Flowchart, Class, State, and Er subsystems lay out through it, and the Sequence, Pie, Gantt, and Mindmap subsystems use its units directly. */

        part clusterLayout : ClusterLayout;
        part shapeLibrary : ShapeLibrary;
        part edgeBuilder : EdgeBuilder;
        part labelBuilder : LabelBuilder;
        part nodeImages : NodeImages;
    }
}
