package CanvasNet {
    part def MermaidScenePainter {
        doc /* The internal ScenePainter of the Mermaid package (a sealed partial class in ScenePainter.cs, ScenePainter.Text.cs, ScenePainter.Images.cs, and ScenePainter.Shadow.cs), the ScenePlacement record struct (Uniform enlarges the view box by a scale at the origin; Fit scales it uniformly by the largest factor that fits a target and centers it, leaving a view box without area unscaled), and the ISceneImageLoader contract. Paint creates a surface, fills it with the background (transparent when none), and draws the items in list order translated by their groups: paths are converted with Scene.ToPath, their drop shadow painted first (the silhouette of the fill and the drawn stroke, rendered into a mask over a scratch region of the shadow's own bounds that is charged whole to the painted-pixel limit, moved by the scaled offset, blurred with the three box blurs of the SVG specification's approximation with the blur clamped at 64 device pixels, and composited in the shadow color), then filled with the core PathFiller under their fill rule, then stroked in device space with PathStroker (scaled width, cap, join, miter limit 4, scaled dashes; a pattern with a negative or non-finite entry, a period under a quarter pixel, or more than 50,000 estimated dashes is drawn solid); text runs are drawn one after the other at the scaled size with the face that the call's FontResolver resolves (CreateFontResolver maps common aliases such as Mermaid's default stack to the bundled Liberation families and never uses installed fonts), anchored at the start, middle, or end, and the glyph outlines of a text with a stroke stroked over the fill; an underlined run gets a bar under its baseline across its advance, at the underline position and thickness of the bundled face's post table; a text line with a rotation is drawn as without it and then turned, glyphs and underline, about its scaled pivot, the box of its turned corners charged, and a line whose angle or pivot is not finite or out of range is not drawn; pictures are requested from the scene's loader at the device size of their box snapped outward to whole pixels, stretched to the box when they come back at another size (preserveAspectRatio none), and composited with the item's opacity, and nothing is drawn without a loader. Every item with a non-finite coordinate or one beyond 32,768 device pixels is skipped; the device box of every shadow, fill, stroke, text line, and picture, clipped to the surface, is charged to MaxPaintedPixels before it is painted and the item that would pass the limit throws a located MermaidRenderException mermaid-limit-exceeded naming the limit; the cancellation token is checked before every item; the created surface is disposed on failure. Deterministic; one painting per instance on one thread. */

        comment sourceRef /* Source: src/DemaConsulting.CanvasNet.Mermaid/Scenegraph/ScenePainter.cs, src/DemaConsulting.CanvasNet.Mermaid/Scenegraph/ScenePainter.Text.cs, src/DemaConsulting.CanvasNet.Mermaid/Scenegraph/ScenePainter.Images.cs, src/DemaConsulting.CanvasNet.Mermaid/Scenegraph/ScenePainter.Shadow.cs */
        comment testRef /* Test: test/DemaConsulting.CanvasNet.Mermaid.Tests/Scenegraph/ScenePainterTests.cs */
        comment designRef /* Design: docs/design/canvas-net-mermaid/scenegraph/scene-painter.md */
        comment verificationRef /* Verification: docs/verification/canvas-net-mermaid/scenegraph/scene-painter.md */
        comment reqRef /* Requirements: docs/reqstream/canvas-net-mermaid/scenegraph/scene-painter.yaml */
    }
}
