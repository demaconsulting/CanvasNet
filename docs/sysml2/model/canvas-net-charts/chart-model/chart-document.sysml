package CanvasNet {
    part def ChartDocument {
        doc /* The Chart, ChartSeries, ChartAxis, ChartLegend, ChartTitle, ChartType, ChartLegendPosition, and ChartBuilder public types: a fully construction-time-validated, immutable chart data model, with a fluent builder API that delegates all validation to the model constructors. */

        comment sourceRef /* Source: src/DemaConsulting.CanvasNet.Charts/Chart.cs, src/DemaConsulting.CanvasNet.Charts/ChartSeries.cs, src/DemaConsulting.CanvasNet.Charts/ChartAxis.cs, src/DemaConsulting.CanvasNet.Charts/ChartLegend.cs, src/DemaConsulting.CanvasNet.Charts/ChartTitle.cs, src/DemaConsulting.CanvasNet.Charts/ChartType.cs, src/DemaConsulting.CanvasNet.Charts/ChartBuilder.cs */
        comment testRef /* Test: test/DemaConsulting.CanvasNet.Charts.Tests/ChartTests.cs, test/DemaConsulting.CanvasNet.Charts.Tests/ChartSeriesTests.cs, test/DemaConsulting.CanvasNet.Charts.Tests/ChartAxisTests.cs, test/DemaConsulting.CanvasNet.Charts.Tests/ChartLegendTests.cs, test/DemaConsulting.CanvasNet.Charts.Tests/ChartTitleTests.cs, test/DemaConsulting.CanvasNet.Charts.Tests/ChartTypeTests.cs, test/DemaConsulting.CanvasNet.Charts.Tests/ChartBuilderTests.cs */
        comment designRef /* Design: docs/design/canvas-net-charts/chart-model/chart-document.md */
        comment verificationRef /* Verification: docs/verification/canvas-net-charts/chart-model/chart-document.md */
        comment reqRef /* Requirements: docs/reqstream/canvas-net-charts/chart-model/chart-document.yaml */
    }
}
