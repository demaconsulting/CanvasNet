package CanvasNet {
    part def OpenXmlChartParser {
        doc /* The OpenXmlChartParser static class and its ChartUnsupportedFeatureException: parses a raw c:chartSpace/c:chart XML element into a validated Chart, reading only cached values (c:numCache/c:strCache) and rejecting an unsupported chart kind or data shape. */

        comment sourceRef /* Source: src/DemaConsulting.CanvasNet.Charts/OpenXml/OpenXmlChartParser.cs, src/DemaConsulting.CanvasNet.Charts/OpenXml/ChartUnsupportedFeatureException.cs */
        comment testRef /* Test: test/DemaConsulting.CanvasNet.Charts.Tests/OpenXmlChartParserTests.cs */
        comment designRef /* Design: docs/design/canvas-net-charts/open-xml-chart/open-xml-chart-parser.md */
        comment verificationRef /* Verification: docs/verification/canvas-net-charts/open-xml-chart/open-xml-chart-parser.md */
        comment reqRef /* Requirements: docs/reqstream/canvas-net-charts/open-xml-chart/open-xml-chart-parser.yaml */
    }
}
